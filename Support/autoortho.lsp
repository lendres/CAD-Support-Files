;;; Copyright Lance A. Endres

(defun C:MIRROR_ORTHO_OFF (/ ORTH SS) 
  (setq ORTH (getvar "orthomode"))
  (setvar "orthomode" 0)
  (setq SS (ssget))
  (command "mirror" SS "" pause pause pause)
  (setvar "orthomode" ORTH)
  (princ)
)

(defun C:MIRROR_ORTHO_ON (/ ORTH SS) 
  (setq ORTH (getvar "orthomode"))
  (setvar "orthomode" 1)
  (setq SS (ssget))
  (command "mirror" SS "" pause pause pause)
  (setvar "orthomode" ORTH)
  (princ)
)

(defun C:ROTATE_ORTHO_OFF (/ ORTH SS) 
  (setq ORTH (getvar "orthomode"))
  (setvar "orthomode" 0)
  (setq SS (ssget))
  (command "rotate" SS "" pause pause)
  (setvar "orthomode" ORTH)
  (princ)
)

(defun C:ROTATE_ORTHO_ON (/ ORTH SS) 
  (setq ORTH (getvar "orthomode"))
  (setvar "orthomode" 1)
  (setq SS (ssget))
  (command "rotate" SS "" pause pause)
  (setvar "orthomode" ORTH)
  (princ)
)

(defun *error* () 
  (setvar "orthomode" ORTH)
)
