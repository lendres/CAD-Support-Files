Attribute VB_Name = "AttUpdating"
Option Explicit
Option Private Module
Option Base 0
Private Attribs As Variant
Private Cnt1 As Long
Public Function VerifyAttribute(ByRef Att As String, ByRef Blk As Variant) As Boolean

    'Establish default value.
    VerifyAttribute = False
    
    'Ensure that capitalization does not prohibit a match.
    Att = LCase(Att)
    
    'Loop through attributes checking for correct one.
    Attribs = Blk.GetAttributes
    For Cnt1 = LBound(Attribs) To UBound(Attribs)
        If LCase(Attribs(Cnt1).TagString) = Att Then
            VerifyAttribute = True
            Exit Function
        End If
    Next Cnt1
    
End Function
Private Sub SetAttVal(ByRef Att As String, ByRef Blk As Object, ByRef Val As Variant)

    'Ensure that capitalization does not prohibit a match.
    Att = LCase(Att)

    'Loop through attributes checking for correct one.
    Attribs = Blk.GetAttributes
    For Cnt1 = LBound(Attribs) To UBound(Attribs)
        If LCase(Attribs(Cnt1).TagString) = Att Then
            Attribs(Cnt1).TextString = Val
            Exit Sub
        End If
    Next Cnt1

End Sub
Public Sub AttUpdate(ByRef FrmVals As Variant)

    'Declare variables.
    Dim Blck As Object
    Dim xDataValue As Variant

    'If the attuseattchbx is false, then the attributes are not to be updated so exit.
    If FrmVals(1) = 0 Then
        Exit Sub
    End If
    
    'If there isn't an entry in the drawing then exit.
    If FrmVals(20) = "" Then
        Exit Sub
    Else
        ThisDrawing.Layers("0").GetXData FrmVals(20), Temp1, xDataValue
    End If

    'Get block name.
    Set Blck = ThisDrawing.HandleToObject(FrmVals(2))
    
    If FrmVals(3) = "Default" Then
    
        If FrmVals(4) = 1 Then
            SetAttVal Att:="DWGPARTNM", Blk:=Blck, Val:=xDataValue(1)
        End If
        If FrmVals(6) = 1 Then
            SetAttVal Att:="DWGREVNO", Blk:=Blck, Val:=xDataValue(2)
        End If
        If FrmVals(8) = 1 Then
            SetAttVal Att:="DWGDATE", Blk:=Blck, Val:=xDataValue(3)
        End If
        If FrmVals(10) = 1 Then
            SetAttVal Att:="DWGMODBY", Blk:=Blck, Val:=xDataValue(4)
        End If
        If FrmVals(12) = 1 Then
            SetAttVal Att:="DWGMODFOR", Blk:=Blck, Val:=xDataValue(5)
        End If
        If FrmVals(14) = 1 Then
            SetAttVal Att:="DWGCHECK1", Blk:=Blck, Val:=xDataValue(6)
        End If
        If FrmVals(16) = 1 Then
            SetAttVal Att:="DWGCHECK2", Blk:=Blck, Val:=xDataValue(7)
        End If
        If FrmVals(18) = 1 Then
            Temp1 = ""
            For Cnt1 = 9 To (9 + xDataValue(8) - 1)
                Temp1 = Temp1 & xDataValue(Cnt1)
            Next Cnt1
            SetAttVal Att:="DWGDESC", Blk:=Blck, Val:=Temp1
        End If

    ElseIf FrmVals(3) = "User" Then
        'Not currently an option.  To be added later (possibly).
    End If

End Sub

Attribute VB_Name = "ConvertVersions"
Option Explicit
Option Base 0
Private Cnt1 As Long
Private Cnt2 As Long
Private NewxDataValue() As Variant
Private Temp1 As Variant
Private xDataCode() As Integer
Private xDataValue As Variant
Option Private Module
Public Sub ConvertV1toV2()
    
    ThisDrawing.Layers("0").GetXData "", Temp1, xDataValue
    
    'If no passed data then exit.
    If IsEmpty(xDataValue) Then
        MsgBox Prompt:="There is no drawing log data in this drawing.", _
                   Title:=DrwLogTitle, Buttons:=vbCritical + vbOKOnly
        Exit Sub
    End If
    
    For Cnt1 = 0 To (UBound(xDataValue) - 9) Step 9
    
        Do While Left(xDataValue(Cnt1), 6) <> "DrwLog"
            If Cnt1 > UBound(xDataValue) - 9 Then
                GoTo EndOfValidData
            End If
            Cnt1 = Cnt1 + 1
        Loop
    
        If (xDataValue(Cnt1)) <> ("DrwLog" & xDataValue(Cnt1 + 2) & xDataValue(Cnt1 + 1)) Then
            
            ReDim xDataCode(9) As Integer
            ReDim NewxDataValue(9) As Variant
            
            xDataCode(0) = 1001
            For Cnt2 = 1 To 7
                xDataCode(Cnt2) = 1000
            Next Cnt2
            xDataCode(8) = 1071
            xDataCode(9) = 1000
            
            NewxDataValue(0) = ("DrwLog" & xDataValue(Cnt1 + 2) & xDataValue(Cnt1 + 1))
            For Cnt2 = 1 To 7
                NewxDataValue(Cnt2) = xDataValue(Cnt1 + Cnt2)
            Next Cnt2
            NewxDataValue(8) = "1"
            NewxDataValue(9) = xDataValue(Cnt1 + 8)
            
            ThisDrawing.Layers("0").SetXData xDataCode, NewxDataValue
            
            RemoveXdata RegAppName:=xDataValue(Cnt1)
        
        End If
                
    Next Cnt1

EndOfValidData:

    MsgBox Prompt:="Drawing log data has been converted from V1 to V2", _
                   Title:=DrwLogTitle, Buttons:=vbCritical + vbOKOnly

End Sub

Attribute VB_Name = "DataConfig"
Attribute VB_Base = "0{99A9B96A-861F-4DF1-9541-4CB4DB1938B5}{E5F77276-DF57-455B-82AB-25DBED1B1EED}"
Attribute VB_GlobalNameSpace = False
Attribute VB_Creatable = False
Attribute VB_PredeclaredId = True
Attribute VB_Exposed = False
Attribute VB_TemplateDerived = False
Attribute VB_Customizable = False
Option Explicit
Option Base 0
Private Const ForAppending As Integer = 8
Private Const ForReading As Integer = 1
Private Const TristateFalse As Integer = 0
Private Sub Cancel_Click()
    Me.hide
End Sub
Private Sub OK_Click()
  
    With Me
    
        If .PartNameTB.Value = True Then
            If ValidateWidth(Frm:=.PartNameWidth) Then
                ConfigDat(0) = .PartNameWidth.Value
            Else
                WidthError
                Exit Sub
            End If
        Else
            ConfigDat(0) = 0
        End If
        
        If .RevNoTB.Value = True Then
            If ValidateWidth(Frm:=.RevNoWidth) Then
                ConfigDat(1) = .RevNoWidth.Value
            Else
                WidthError
                Exit Sub
            End If
        Else
            ConfigDat(1) = 0
        End If
        
        If .DateTB.Value = True Then
            If ValidateWidth(Frm:=.DateWidth) Then
                ConfigDat(2) = .DateWidth.Value
            Else
                WidthError
                Exit Sub
            End If
        Else
            ConfigDat(2) = 0
        End If
        
        If .ModByTB.Value = True Then
            If ValidateWidth(Frm:=.ModByWidth) Then
                ConfigDat(3) = .ModByWidth.Value
            Else
                WidthError
                Exit Sub
            End If
        Else
            ConfigDat(3) = 0
        End If
        
        If .ModForTB.Value = True Then
            If ValidateWidth(Frm:=.ModForWidth) Then
                ConfigDat(4) = .ModForWidth.Value
            Else
                WidthError
                Exit Sub
            End If
        Else
            ConfigDat(4) = 0
        End If
        
        If .CheckBy1TB.Value = True Then
            If ValidateWidth(Frm:=.CheckBy1Width) Then
                ConfigDat(5) = .CheckBy1Width.Value
            Else
                WidthError
                Exit Sub
            End If
        Else
            ConfigDat(5) = 0
        End If
        
        If .CheckBy2TB.Value = True Then
            If ValidateWidth(Frm:=.CheckBy2Width) Then
                ConfigDat(6) = .CheckBy2Width.Value
            Else
                WidthError
                Exit Sub
            End If
        Else
            ConfigDat(6) = 0
        End If
        
        If .DescTB.Value = True Then
            If ValidateWidth(Frm:=.DescWidth) Then
                ConfigDat(7) = .DescWidth.Value
            Else
                WidthError
                Exit Sub
            End If
        Else
            ConfigDat(7) = 0
        End If
    End With
    
    'Test to ensure that at least one value is to be exported.
    For Cnt1 = 0 To 7
        Temp1 = Temp1 + ConfigDat(Cnt1)
    Next Cnt1
    
    'If temp1 = 0 then all the extries are to be exclude from exporting.
    'This is not allowed.
    If Temp1 = 0 Then
    
        MsgBox Prompt:="At least one entry must be set to export.", _
            Title:=DrwLogTitle, Buttons:=vbCritical + vbOKOnly
            
    Else
    
        'If the program makes it this far, then all the data is ok and
        'now it is written to the file.
    
        'Open file
        FileNum = FreeFile
        Open DwgLogFile For Output As #FileNum
    
        'Write data
        For Cnt1 = 0 To 7
            Write #FileNum, CDbl(ConfigDat(Cnt1))
        Next Cnt1
    
        'Close file
        Close #FileNum
   
        Me.hide
        
    End If
    
End Sub
Private Sub PartNameTB_Change()
    With Me
        Temp1 = .PartNameTB.Value
        .PartNameWidth.Visible = Temp1
    End With
End Sub
Private Sub PartNameWidth_Exit(ByVal Cancel As MSForms.ReturnBoolean)
    Temp1 = ValidateWidth(Frm:=Me.PartNameWidth)
    If Not (Temp1) Then
        WidthError
    End If
End Sub
Private Sub RevNoTB_Change()
    With Me
        Temp1 = .RevNoTB.Value
        .RevNoWidth.Visible = Temp1
    End With
End Sub
Private Sub RevNoWidth_Exit(ByVal Cancel As MSForms.ReturnBoolean)
    Temp1 = ValidateWidth(Frm:=Me.RevNoWidth)
    If Not (Temp1) Then
        WidthError
    End If
End Sub
Private Sub DateTB_Change()
    With Me
        Temp1 = .DateTB.Value
        .DateWidth.Visible = Temp1
    End With
End Sub
Private Sub DateWidth_Exit(ByVal Cancel As MSForms.ReturnBoolean)
    Temp1 = ValidateWidth(Frm:=Me.DateWidth)
    If Not (Temp1) Then
        WidthError
    End If
End Sub
Private Sub ModByTB_Change()
    With Me
        Temp1 = .ModByTB.Value
        .ModByWidth.Visible = Temp1
    End With
End Sub
Private Sub ModByWidth_Exit(ByVal Cancel As MSForms.ReturnBoolean)
    Temp1 = ValidateWidth(Frm:=Me.ModByWidth)
    If Not (Temp1) Then
        WidthError
    End If
End Sub
Private Sub ModForTB_Change()
    With Me
        Temp1 = .ModForTB.Value
        .ModForWidth.Visible = Temp1
    End With
End Sub
Private Sub ModForWidth_Exit(ByVal Cancel As MSForms.ReturnBoolean)
    Temp1 = ValidateWidth(Frm:=Me.ModForWidth)
    If Not (Temp1) Then
        WidthError
    End If
End Sub
Private Sub CheckBy1TB_Change()
    With Me
        Temp1 = .CheckBy1TB.Value
        .CheckBy1Width.Visible = Temp1
    End With
End Sub
Private Sub CheckBy1Width_Exit(ByVal Cancel As MSForms.ReturnBoolean)
    Temp1 = ValidateWidth(Frm:=Me.CheckBy1Width)
    If Not (Temp1) Then
        WidthError
    End If
End Sub
Private Sub CheckBy2TB_Change()
    With Me
        Temp1 = .CheckBy2TB.Value
        .CheckBy2Width.Visible = Temp1
    End With
End Sub
Private Sub CheckBy2Width_Exit(ByVal Cancel As MSForms.ReturnBoolean)
    Temp1 = ValidateWidth(Frm:=Me.CheckBy2Width)
    If Not (Temp1) Then
        WidthError
    End If
End Sub
Private Sub DescTB_Change()
    With Me
        Temp1 = .DescTB.Value
        .DescWidth.Visible = Temp1
    End With
End Sub
Private Sub DescWidth_Exit(ByVal Cancel As MSForms.ReturnBoolean)
    Temp1 = ValidateWidth(Frm:=Me.DescWidth)
    If Not (Temp1) Then
        WidthError
    End If
End Sub
Private Sub UserForm_Initialize()

    'Initilize variables
    FileNum = FreeFile
    DwgLogFile = GetDwgLogCfgFile
    
    InsureConfigData FileName:=DwgLogFile
        
    'Open the config file for input
    Open DwgLogFile For Input As #FileNum
    
    'Read in the config data and store in the ConfigDat array variable
    Cnt1 = 0
    Do While Not EOF(FileNum)
        Line Input #FileNum, ConfigDat(Cnt1)
        Cnt1 = Cnt1 + 1
    Loop
    
    'Close the file
    Close #FileNum
    
    'Set initial values of forms
    With Me
    
        'Part Name
        If ConfigDat(0) = 0 Then
            .PartNameTB.Value = False
            .PartNameWidth.Visible = False
        Else
            .PartNameWidth.Value = ConfigDat(0)
        End If
        
        'Revision number
        If ConfigDat(1) = 0 Then
            .RevNoTB.Value = False
            .RevNoWidth.Visible = False
        Else
            .RevNoWidth.Value = ConfigDat(1)
        End If
        
        'Date
        If ConfigDat(2) = 0 Then
            .DateTB.Value = False
            .DateWidth.Visible = False
        Else
            .DateWidth.Value = ConfigDat(2)
        End If
        
        'Modified By
        If ConfigDat(3) = 0 Then
            .ModByTB.Value = False
            .ModByWidth.Visible = False
        Else
            .ModByWidth.Value = ConfigDat(3)
        End If
        
        'Modified For
        If ConfigDat(4) = 0 Then
            .ModForTB.Value = False
            .ModForWidth.Visible = False
        Else
            .ModForWidth.Value = ConfigDat(4)
        End If
        
        'Checked by 1
        If ConfigDat(5) = 0 Then
            .CheckBy1TB.Value = False
            .CheckBy1Width.Visible = False
        Else
            .CheckBy1Width.Value = ConfigDat(5)
        End If
        
        'Checked by 2
        If ConfigDat(6) = 0 Then
            .CheckBy2TB.Value = False
            .CheckBy2Width.Visible = False
        Else
            .CheckBy2Width.Value = ConfigDat(6)
        End If
        
        'Description
        If ConfigDat(7) = 0 Then
            .DescTB.Value = False
            .DescWidth.Visible = True
        Else
            .DescWidth.Value = ConfigDat(7)
        End If
    
    End With
End Sub
Private Sub WidthError()
    MsgBox Prompt:="Width must be numeric and 1 or greater in value.", Title:=DrwLogTitle, Buttons:=vbCritical + vbOKOnly
End Sub
Private Function ValidateWidth(Frm As Object) As Boolean
    
    'Retrieve form value
    Temp1 = Frm.Value
    
    'Check to make sure entry is a number and 1 or greater
    If Not (IsNumeric(Temp1)) Or Temp1 < 1 Then
        ValidateWidth = False
    Else
        ValidateWidth = True
    End If

End Function

Attribute VB_Name = "DataExport"
Option Explicit
Private xDataValue As Variant
Public Sub SolidWorksExport()

    Dim aDoc As Object
    Dim aSheet As Object
    Dim ExcelApp As Object
    Dim NumEntry As Integer
    Dim RowCnt As Long

    Const StrtCell As String = "A1"
    
    NumEntry = 7
    
    Set aDoc = AutoCAD.Application.ActiveDocument
    
    ThisDrawing.Layers("0").GetXData "", Temp1, xDataValue
    
    'If DwgLogData is false, the the layer 0 contains xData that is not from DrwLog and it must be removed.
     xDataValue = VerifyDrwLogData(Dat:=xDataValue)


    'Verify that this drawing contains DrwLog entrys after the non DrwLog xData has been removed.
    If IsEmpty(xDataValue) Then
        Exit Sub
    End If

    aDoc.SetVariable "modemacro", "Initilizing Excel..."
    
    'Get data from config file.
    
    'Initilize variables.
    FileNum = FreeFile
    DwgLogFile = GetDwgLogCfgFile
    
    'Insure data exists to prevent errors.
    InsureConfigData FileName:=DwgLogFile
    
    'Open the config file for input.
    Open DwgLogFile For Input As #FileNum
    
    'Read in the config data and store in the ConfigDat array variable.
    Cnt1 = 0
    
    Do While Not EOF(FileNum)
        
        'Read in a line.
        Line Input #FileNum, Temp1
        
        ConfigDat(Cnt1) = CInt(Temp1)
            
        'Increment counter.
        Cnt1 = Cnt1 + 1
        
    Loop
    
    'Close the file.
    Close #FileNum
    
    'Create a new Excel object.
    Set ExcelApp = CreateObject("Excel.Application")
    
    'Set up sheets.
    With ExcelApp
        Temp1 = .SheetsInNewWorkbook
        .SheetsInNewWorkbook = 1
        .Workbooks.Add
        .SheetsInNewWorkbook = Temp1
        .ActiveWindow.Zoom = 85
    End With
    
    Set aSheet = ExcelApp.ActiveSheet

    With aSheet
    
        .Name = "Drawing Log"

        'Label column headings.
        With .Range(StrtCell)
            .Offset(0, 0).FormulaR1C1 = "Part No."
            .Offset(0, 1).FormulaR1C1 = "Rev No."
            .Offset(0, 2).FormulaR1C1 = "Date"
            .Offset(0, 3).FormulaR1C1 = "Modified By"
            .Offset(0, 4).FormulaR1C1 = "Modified For"
            .Offset(0, 5).FormulaR1C1 = "Checked By 1"
            .Offset(0, 6).FormulaR1C1 = "Checked By 2"
            .Offset(0, 7).FormulaR1C1 = "Description"
        End With

        'Add data to sheet.
        
        'Step through each drawing log entry.
        RowCnt = 1
        For Cnt1 = 0 To (UBound(xDataValue) - 9) Step 9
        
            'Step through each value in the log entry.
            For Cnt2 = 1 To 7
                    
               .Range(StrtCell).Offset(RowCnt, (Cnt2 - 1)).FormulaR1C1 = xDataValue(Cnt1 + Cnt2)
            
            Next Cnt2
            
            'Get all the description entries and put into cell.
            Temp1 = ""
            For Cnt2 = 9 To 8 + xDataValue(Cnt1 + 8)
                Temp1 = Temp1 & xDataValue(Cnt1 + Cnt2)
            Next Cnt2
            .Range(StrtCell).Offset(RowCnt, NumEntry).FormulaR1C1 = Temp1
            
            'Outline the borders.
            'OutLineBorders Sht:=aSheet, Strt:=.Range(StrtCell).Offset(RowCnt, 0).Address, Numb:=NumEntry
            
            'Increment row counter.
            RowCnt = RowCnt + 1
            
            'If there is more than one description entry the cnt1 needs to be incremented also
            Cnt1 = Cnt1 + xDataValue(Cnt1 + 8)

        Next Cnt1
        
        'Sort data.
        .Range(.Range(StrtCell).Offset(1, 0), .Range(StrtCell).Offset(RowCnt, NumEntry)).Sort _
             Key1:=.Range(StrtCell).Offset(1, 1), Order1:=1, Key2:=.Range(StrtCell).Offset(1, 2) _
             , Order2:=1, Key3:=.Range(StrtCell).Offset(1, 0), Order3:=1, Header:= _
             2, OrderCustom:=1, MatchCase:=False, Orientation:=1

        'Format columns.
        With .Range(StrtCell)
        
            For Cnt1 = 0 To 7
            
                If ConfigDat(Cnt1) = 0 Then
                
                    'If it is zero, delete column.
                    'Delete column and shift to left, xlToLeft.
                    ExcelApp.ActiveSheet.Columns(Cnt1 + 2).Delete Shift:=-4159
                    
                    'Check to see if it is to exported, increment the number.
                    'of entries if it is to be exported.
                    NumEntry = NumEntry - 1
                
                Else
                
                    'Revision number.
                    .Offset(0, (Cnt1 - (7 - NumEntry))).EntireColumn.ColumnWidth = ConfigDat(Cnt1)
                    
                End If
                
            Next Cnt1
            
            'Format date column.
            If ConfigDat(2) <> 0 Then
                With .Offset(0, 2).EntireColumn
                    .NumberFormat = "mm/dd/yyyy"
                End With
            End If
            
            For Cnt1 = 0 To NumEntry
                With .Offset(0, Cnt1).EntireColumn
                    'Vertical alignment xlTop
                    .VerticalAlignment = -4160
                    .WrapText = True
                End With
            Next Cnt1
            
            'Outline borders for header columns.
            'OutLineBorders Sht:=aSheet, Strt:=.Offset(0, 0).Address, Numb:=NumEntry
        
        End With
        
        'Format column headings.
        With .Range(.Range(StrtCell).Offset(0, 0), .Range(StrtCell).Offset(0, NumEntry))
            .Font.Bold = True
            .HorizontalAlignment = -4108
            .VerticalAlignment = -4107
            .WrapText = False
            .Orientation = 0
            .AddIndent = False
            .ShrinkToFit = False
            .MergeCells = False
            
            .Select
        End With
        
        'Select cell A1.
        .Range("A1").Select
    
    End With
    
    aDoc.SetVariable "modemacro", ""
    
    'Display the Excel application.
    'ExcelApp.Visible = True
    
    'Turn off over write existing file warning.
    ExcelApp.DisplayAlerts = False
    
    'Save the file.
    Dim drawingName As String
    Dim stringLength As Integer
    
    drawingName = aDoc.Name
    drawingName = aDoc.FullName
    stringLength = Len(drawingName)
    drawingName = Left(drawingName, stringLength - 4) + ".xlsx"
    ExcelApp.ActiveWorkbook.SaveAs FileName:=drawingName
    
    'Turn over write existing file warning back on.
    ExcelApp.DisplayAlerts = True
    
    'Close Excel.
    ExcelApp.Quit
    
End Sub
Private Sub OutLineBorders(Sht As Object, Strt As String, Numb As Integer)
    With Sht.Range(Strt, Sht.Range(Strt).Offset(0, Numb))
        .Borders(5).LineStyle = -4142
        .Borders(6).LineStyle = -4142
        With .Borders(7)
            .LineStyle = 1
            .Weight = 2
            .ColorIndex = -4105
        End With
        With .Borders(8)
            .LineStyle = 1
            .Weight = 2
            .ColorIndex = -4105
        End With
        With .Borders(9)
            .LineStyle = 1
            .Weight = 2
            .ColorIndex = -4105
        End With
        With .Borders(10)
            .LineStyle = 1
            .Weight = 2
            .ColorIndex = -4105
        End With
        With .Borders(11)
            .LineStyle = 1
            .Weight = 2
            .ColorIndex = -4105
        End With
    End With

End Sub

Attribute VB_Name = "DrawLog"
Option Explicit
Public DwgLogAttSelectBlock As Boolean
Public DwgLogAttBlock As Variant
Sub RunDrawLog()

    'Declare variables.
    Dim aFrm As Object
    
    'Initialize variables.
    'DwgLogAttSelectBlock will be used to test if the select block button was _
     used to hide the form.
    DwgLogAttSelectBlock = False
    
    'Start a new instance of DrawLogFrm.
    Set aFrm = New DrawLogFrm
    
    'Load and run the form.
    Load aFrm

    aFrm.Show
    
AttSelectBlock:
    If DwgLogAttSelectBlock Then

        'Get a block that has attributes.
        GetAttBlock AttBlock:=DwgLogAttBlock

        'Show the form again.
        aFrm.Show
        
        'Retest for exit method.
        GoTo AttSelectBlock
        
    End If
    
    'Unload the form to reset values and restore memory.
    Unload aFrm

End Sub

Attribute VB_Name = "DrawLogFrm"
Attribute VB_Base = "0{AD6578BC-1EB2-44F8-9CD9-883C4C6B4A30}{6FD96160-1F5C-46B2-8BE5-2EF65DA87ED9}"
Attribute VB_GlobalNameSpace = False
Attribute VB_Creatable = False
Attribute VB_PredeclaredId = True
Attribute VB_Exposed = False
Attribute VB_TemplateDerived = False
Attribute VB_Customizable = False
Option Explicit
Option Base 0
Option Compare Text
Private CntrlState As Variant
Private DwgFrm As Object
Private DwgLogxDataOnly As Boolean
Private DxfCode As Variant
Private RevNo As String
Private xDataValue As Variant
Private xDtVl As Variant
Private Sub AttPartNoTB_Change()
    With Me
        Temp1 = .AttPartNoTB.Value
        .AttPartLbl.Enabled = Temp1
        .AttPartName.Enabled = Temp1
    End With
End Sub
Private Sub AttRevNoTB_Change()
    With Me
        Temp1 = .AttRevNoTB.Value
        .AttRevLbl.Enabled = Temp1
        .AttRevNoName.Enabled = Temp1
    End With
End Sub
Private Sub AttDateTB_Change()
    With Me
        Temp1 = .AttDateTB.Value
        .AttDateLbl.Enabled = Temp1
        .AttDateName.Enabled = Temp1
    End With
End Sub
Private Sub AttModByTB_Change()
    With Me
        Temp1 = .AttModByTB.Value
        .AttModByLbl.Enabled = Temp1
        .AttModByName.Enabled = Temp1
    End With
End Sub
Private Sub AttModForTB_Change()
    With Me
        Temp1 = .AttModForTB.Value
        .AttModForLbl.Enabled = Temp1
        .AttModForName.Enabled = Temp1
    End With
End Sub
Private Sub AttCheck1TB_Change()
    With Me
        Temp1 = .AttCheck1TB.Value
        .AttCheck1Lbl.Enabled = Temp1
        .AttCheck1Name.Enabled = Temp1
    End With
End Sub
Private Sub AttCheck2TB_Change()
    With Me
        Temp1 = .AttCheck2TB.Value
        .AttCheck2Lbl.Enabled = Temp1
        .AttCheck2Name.Enabled = Temp1
    End With
End Sub
Private Sub AttDescTB_Change()
    With Me
        Temp1 = .AttDescTB.Value
        .AttDescLbl.Enabled = Temp1
        .AttDescName.Enabled = Temp1
    End With
End Sub
Private Sub AttSelectBtn_Click()

    'Restore the false status to prevent accidental loop.
    DwgLogAttSelectBlock = True
    
    'Hide the form so that the block can be selected.
    Me.hide

End Sub
Private Sub AttError()
    DwgError Prmpt:="Active attributes not found in the selected block." & vbCrLf & _
        "All attributes selected have to be present in the block."
End Sub
Private Sub AttUseAttChBx_Change()
    With Me
        Temp1 = .AttUseAttChBx.Value
        
        '.AttSelectLbl.Enabled = Temp1
        .AttSelectBtn.Enabled = Temp1
        
        .AttBlockLbl.Enabled = Temp1
        .AttBlockName.Enabled = Temp1
        
        '.AttDfltLbl.Enabled = Temp1
        '.AttDfltTB.Enabled = Temp1
        
        .AttPartNoTB.Enabled = Temp1
        If .AttPartNoTB.Value Then
            .AttPartLbl.Enabled = Temp1
            .AttPartName.Enabled = Temp1
        End If
        
        .AttRevNoTB.Enabled = Temp1
        If .AttRevNoTB.Value Then
            .AttRevLbl.Enabled = Temp1
            .AttRevNoName.Enabled = Temp1
        End If
        
        .AttDateTB.Enabled = Temp1
        If .AttDateTB.Value Then
            .AttDateLbl.Enabled = Temp1
            .AttDateName.Enabled = Temp1
        End If

        .AttModByTB.Enabled = Temp1
        If .AttModByTB.Value Then
            .AttModByLbl.Enabled = Temp1
            .AttModByName.Enabled = Temp1
        End If
        
        .AttModForTB.Enabled = Temp1
        If .AttModForTB.Value Then
            .AttModForLbl.Enabled = Temp1
            .AttModForName.Enabled = Temp1
        End If

        .AttCheck1TB.Enabled = Temp1
        If .AttCheck1TB.Value Then
            .AttCheck1Lbl.Enabled = Temp1
            .AttCheck1Name.Enabled = Temp1
        End If

        .AttCheck2TB.Enabled = Temp1
        If .AttCheck2TB.Value Then
            .AttCheck2Lbl.Enabled = Temp1
            .AttCheck2Name.Enabled = Temp1
        End If

        .AttDescTB.Enabled = Temp1
        If .AttDescTB.Value Then
            .AttDescLbl.Enabled = Temp1
            .AttDescName.Enabled = Temp1
        End If

    End With
    
End Sub
Private Sub ConvertVersCmd_Click()
    ConvertV1toV2
    
    'Get extended data and populate the forms with it
    ThisDrawing.Layers("0").GetXData "", Temp1, xDataValue
    
    'Set default value of DwgLogData
    'Me.DwgLogData = True
    
    xDataValue = VerifyDrwLogData(Dat:=xDataValue)
    DrwLogPopForms xDataVal:=xDataValue
    DrwLogPopSrchFrms xDataVal:=xDataValue
    
    'Clear search page form entries.
    ClearSearchPageForms
    
End Sub
Private Sub UseAttsLbl_Click()
    With Me
        .AttUseAttChBx.Value = Not (.AttUseAttChBx.Value)
    End With
End Sub
Private Sub UserForm_Activate()
    
    If DwgLogAttSelectBlock Then

        If VarType(DwgLogAttBlock) = 9 Then
            VerifyAttBlock
        End If
        
        'Restore the false status to prevent accidental loop.
        DwgLogAttSelectBlock = False
        
    End If

End Sub
Private Sub VerifyAttBlock()

    With Me
    
        'Part Number.
        If .AttPartNoTB.Value Then
            If Not (VerifyAttribute(Att:=.AttPartName, Blk:=DwgLogAttBlock)) Then
                AttError
                Exit Sub
            End If
        End If
        
        'Revision Number.
        If .AttRevNoTB.Value Then
            If Not (VerifyAttribute(Att:=.AttRevNoName, Blk:=DwgLogAttBlock)) Then
                AttError
                Exit Sub
            End If
        End If
        
        'Date.
        If .AttDateTB.Value Then
            If Not (VerifyAttribute(Att:=.AttDateName, Blk:=DwgLogAttBlock)) Then
                AttError
                Exit Sub
            End If
        End If
        
        'Modified By.
        If .AttModByTB.Value Then
            If Not (VerifyAttribute(Att:=.AttModByName, Blk:=DwgLogAttBlock)) Then
                AttError
                Exit Sub
            End If
        End If
        
        'Modified For.
        If .AttModForTB.Value Then
            If Not (VerifyAttribute(Att:=.AttModForName, Blk:=DwgLogAttBlock)) Then
                AttError
                Exit Sub
            End If
        End If
        
        'Checked By 1.
        If .AttCheck1TB.Value Then
            If Not (VerifyAttribute(Att:=.AttCheck1Name, Blk:=DwgLogAttBlock)) Then
                AttError
                Exit Sub
            End If
        End If
        
        'Checked By 2.
        If .AttCheck2TB.Value Then
            If Not (VerifyAttribute(Att:=.AttCheck2Name, Blk:=DwgLogAttBlock)) Then
                AttError
                Exit Sub
            End If
        End If
        
        'Description.
        If .AttDescTB.Value Then
            If Not (VerifyAttribute(Att:=.AttDescName, Blk:=DwgLogAttBlock)) Then
            
            End If
        End If
    
        'If the sub made it this far with out exiting, then all the necessary _
         attributes are present in the block.
         
        'Set the block name text box
        .AttBlockName.Caption = DwgLogAttBlock.Name
    
    End With
         
    GoTo VerifyExit:
         
AttNotFound:
         
    AttError
    DwgLogAttBlock = False
 
VerifyExit:

End Sub
Private Sub UserForm_Initialize()

    'Get extended data and populate the forms with it
    ThisDrawing.Layers("0").GetXData "", Temp1, xDataValue
    
    'Set default value of DwgLogData
    'Me.DwgLogData = True
    
    xDataValue = VerifyDrwLogData(Dat:=xDataValue)
    DrwLogPopForms xDataVal:=xDataValue
    DrwLogPopSrchFrms xDataVal:=xDataValue
    
    'Clear search page form entries.
    ClearSearchPageForms
    
    'Initilize the Attribute Maintance Page.
    AttInitMaintainance
    
End Sub
Private Sub AttDfltTB_Change()

    ThisDrawing.Layers("0").GetXData "DwgLogAttInfo", Temp1, xDataValue
    
    With Me
        If .AttDfltTB.Value = True Then
            .AttPartName.Caption = "DWGPARTNM"
            .AttRevNoName.Caption = "DWGREVNO"
            .AttDateName.Caption = "DWGDATE"
            .AttModByName.Caption = "DWGMODBY"
            .AttModForName.Caption = "DWGMODFOR"
            .AttCheck1Name.Caption = "DWGCHECK1"
            .AttCheck2Name.Caption = "DWGCHECK2"
            .AttDescName.Caption = "DWGDESC"
            xDataValue(3) = "Default"
            ThisDrawing.Layers("0").SetXData Temp1, xDataValue
        Else
            AttNameVals Vals:=xDataValue
            xDataValue(3) = "User"
            ThisDrawing.Layers("0").SetXData Temp1, xDataValue
        End If
        
    End With
    
End Sub
Private Sub AttNameVals(ByRef Vals As Variant)
    
    Temp1 = 5
    
    With Me
        .AttPartName.Caption = Vals(Temp1)
        .AttRevNoName.Caption = Vals(Temp1 + 2)
        .AttDateName.Caption = Vals(Temp1 + 4)
        .AttModByName.Caption = Vals(Temp1 + 6)
        .AttModForName.Caption = Vals(Temp1 + 8)
        .AttCheck1Name.Caption = Vals(Temp1 + 10)
        .AttCheck2Name.Caption = Vals(Temp1 + 12)
        .AttDescName.Caption = Vals(Temp1 + 14)
    End With
    
End Sub
Private Sub AttInitMaintainance()

    'Get data if it exists.
    ThisDrawing.Layers("0").GetXData "DwgLogAttInfo", DxfCode, xDataValue
    
    'Make sure that the attribute updating buttons will have valid data to set themselves.
    'This was added 01/18/2004 to fix a problem where a drawing had bad data that was used
    'to try to set the forms on the attribute page.
    Dim BadData As Boolean
    BadData = False
    If Not (IsEmpty(xDataValue)) Then
        'If the data is there make sure it is ok.
        If Not (xDataValue(1) = 0) And Not (xDataValue(1) = 1) Then
            'If it isn't ok send a message to the user to let them know,
            'then clear the data so that the default values below will get installed.
            MsgBox Prompt:="Bad data for the attribute updating was stored in this drawing." + _
                Chr(10) + "Warning: This data WILL be erased.", _
                Title:="Data Error", Buttons:=vbCritical + vbOKOnly
            Erase DxfCode
            Erase xDataValue
            'Because xDataValue had been initialized to some bad data it will _
             no longer issue true when IsEmpty(xDataValue) is used so instead I _
             will just use this flag to make sure the data is reset.
            BadData = True
        End If
    End If
    
    'If it doesn't exist store a not installed value
    With Me
    
        If IsEmpty(xDataValue) Or BadData Then
        
            'Size arrays
            ReDim DxfCode(20) As Integer
            ReDim xDataValue(20) As Variant
            
            'Create group code entries
            DxfCode(0) = 1001
            DxfCode(1) = 1070
            For Cnt1 = 2 To 3
                DxfCode(Cnt1) = 1000
            Next Cnt1
            For Cnt1 = 4 To 18 Step 2
                DxfCode(Cnt1) = 1070
            Next Cnt1
            For Cnt1 = 5 To 19 Step 2
                DxfCode(Cnt1) = 1000
            Next Cnt1
            DxfCode(20) = 1000
            
            'Create default values
            
            'Registered Application Name
            xDataValue(0) = "DwgLogAttInfo"
            
            'Installed = 0 / Not Installed = 1
            xDataValue(1) = 0
            
            'Block Handle (string)
            xDataValue(2) = ""
            
            '"Default" Attributes / "User" Attributes
            xDataValue(3) = "Default"
            
            '4 to 8 Evens - Use status of attribues _
             1 Use / 0 Don't use
            For Cnt1 = 4 To 18 Step 2
                xDataValue(Cnt1) = 1
            Next Cnt1
            
            '5 to 19 Odds - Attribute name
            For Cnt1 = 5 To 19 Step 2
                xDataValue(Cnt1) = ""
            Next Cnt1
            
            'Registered Application Name of the entry that contains the values _
             to use as the attribute tags.
            xDataValue(20) = ""
            
            ThisDrawing.Layers("0").SetXData DxfCode, xDataValue
            
        End If
        
        .AttUseAttChBx.Value = xDataValue(1)
        
        If xDataValue(3) = "Default" Then
            .AttDfltTB.Value = True
        Else
            AttNameVals Vals:=xDataValue
            .AttUseAttChBx.Value = True
        End If
        
        Cnt1 = 4
        .AttPartNoTB.Value = xDataValue(Cnt1)
        .AttRevNoTB.Value = xDataValue(Cnt1 + 2)
        .AttDateTB.Value = xDataValue(Cnt1 + 4)
        .AttModByTB.Value = xDataValue(Cnt1 + 6)
        .AttModForTB.Value = xDataValue(Cnt1 + 8)
        .AttCheck1TB.Value = xDataValue(Cnt1 + 10)
        .AttCheck2TB.Value = xDataValue(Cnt1 + 12)
        .AttDescTB.Value = xDataValue(Cnt1 + 14)
        
        'Block name.
        If xDataValue(2) <> "" Then
        
            'Get handle and use it to return block, if the block has been erased, then _
             an error will result
            On Error GoTo InvalidHandle
            
            Set Temp1 = ThisDrawing.HandleToObject(xDataValue(2))
            .AttBlockName.Caption = Temp1.Name
            GoTo ValidHandle
            
InvalidHandle:
            MsgBox Prompt:="The block designated for attribute updating is no longer valid", _
                            Title:=DrwLogTitle, Buttons:=vbCritical + vbOKOnly
            xDataValue(2) = ""
            ThisDrawing.Layers("0").SetXData DxfCode, xDataValue
            
ValidHandle:
            On Error GoTo 0
            
        End If
    
    End With
    
End Sub
Private Function AttWriteStatus() As Boolean

    'Default status.
    AttWriteStatus = False

    'Get data if it exists.
    ThisDrawing.Layers("0").GetXData "DwgLogAttInfo", DxfCode, xDataValue

    'If it doesn't exist don't bother.
    If IsEmpty(xDataValue) Then
        Exit Function
    End If
    
    'Check for valid data, the values will be added to the xdatavalue variable.
    If AttGetFormStatus(Dat:=xDataValue) Then
        ThisDrawing.Layers("0").SetXData DxfCode, xDataValue
        AttWriteStatus = True
    End If
    
End Function
Private Function AttGetFormStatus(ByRef Dat As Variant) As Boolean
    
    'Default status
    AttGetFormStatus = True
   
    With Me
    
        'Check to see if the use attrubute updating is used and the block name _
         does not exist.  If it doesn't then attribute updating has been turned _
         on with out selecting a block.
         
         If .AttUseAttChBx And (Trim(.AttBlockName) = "") Then
             MsgBox Prompt:="A block for attribute updating has not been selected." & vbCrLf & _
                            "Select a valid block or turn off attribute updating.", _
                            Title:=DrwLogTitle, Buttons:=vbCritical + vbOKOnly
            AttGetFormStatus = False
            Exit Function
        End If

        'Get the handle of the block to use from the gobal variable. _
         If the block is not false, then it has either not been used or _
         been used and did not pass the tests.
         
        If VarType(DwgLogAttBlock) = 9 Then
        
            'Get handle and use it to return block, if the block has been erased, then _
             an error will result
            On Error GoTo InvalidHandle
            
            Dat(2) = DwgLogAttBlock.Handle
            GoTo ValidHandle
            
InvalidHandle:
            If .AttUseAttChBx.Value Then
            
                'If the use attribute updating is checked and the block is missing _
                 issue an error, and return a false to the ok_click procedure, telling _
                 it not to exit.
                MsgBox Prompt:="The block designated for attribute updating is no longer valid", _
                                Title:=DrwLogTitle, Buttons:=vbCritical + vbOKOnly
                
                AttGetFormStatus = False
                Exit Function
            
            End If
        
ValidHandle:
            On Error GoTo 0
            
        End If
    
        If .AttUseAttChBx.Value Then
            Dat(1) = 1
        Else
            Dat(1) = 0
        End If
        
        If .AttDfltTB.Value Then
            Dat(3) = "Default"
        Else
            Dat(3) = "User"
        End If
        
        If .AttPartNoTB.Value Then
            Dat(4) = 1
        Else
            Dat(4) = 0
        End If
        
        Dat(5) = .AttPartName.Caption
        
        If .AttRevNoTB.Value Then
            Dat(6) = 1
        Else
            Dat(6) = 0
        End If
        
        Dat(7) = .AttRevNoName.Caption
        
        If .AttDateTB.Value Then
            Dat(8) = 1
        Else
            Dat(8) = 0
        End If
        
        Dat(9) = .AttDateName.Caption
        
        If .AttModByTB.Value Then
            Dat(10) = 1
        Else
            Dat(10) = 0
        End If
        
        Dat(11) = .AttModByName.Caption
        
        If .AttModForTB.Value Then
            Dat(12) = 1
        Else
            Dat(12) = 0
        End If
        
        Dat(13) = .AttModForName.Caption
        
        If .AttCheck1TB.Value Then
            Dat(14) = 1
        Else
            Dat(14) = 0
        End If
        
        Dat(15) = .AttCheck1Name.Caption
        
        If .AttCheck2TB.Value Then
            Dat(16) = 1
        Else
            Dat(16) = 0
        End If
        
        Dat(17) = .AttCheck2Name.Caption
        
        If .AttDescTB.Value Then
            Dat(18) = 1
        Else
            Dat(18) = 0
        End If
        
        Dat(19) = .AttDescName.Caption
        
    End With

End Function
Private Sub DataExpConfig_Click()
    
    'Declare variables.
    Dim aFrm As Object
    
    'Start a new instance of DrawLogFrm.
    Set aFrm = New DataConfig
    
    'Load and run the form.
    Load aFrm
    aFrm.Show
    
    'Unload the form to reset values and restore memory.
    Unload aFrm
End Sub
Private Sub DrwLogPopForms(xDataVal As Variant)

    'Declare variables
    Dim Cnt1 As Integer
    Dim NewRev(1) As String
    Dim Pstn As Integer
    
    With Me
    
        'Clear forms on add/modify page
    
        .PartNoBox.Clear
        .RevNoBox.Clear
        .ModByBox.Clear
        .ModForBox.Clear
        .Check1Box.Clear
        .Check2Box.Clear
        
        ClearForms

        'If there is no data exit sub.
        If IsMissing(xDataVal) Or IsEmpty(xDataVal) Then
            Exit Sub
        End If
        
        'Initiate variables
        
        NewRev(0) = xDataVal(1)
        NewRev(1) = xDataVal(2)
        Pstn = 0
   
        'Extract data and assign to appropriate forms.

        For Cnt1 = 0 To (UBound(xDataVal) - 9) Step 9

            'Track newest entry
            
            If CDate(xDataVal(Pstn + 3)) < CDate(xDataVal(Cnt1 + 3)) Or _
               (CDate(xDataVal(Pstn + 3)) = CDate(xDataVal(Cnt1 + 3)) And xDataVal(Pstn + 2) < xDataVal(Cnt1 + 2)) Then
                
                'Record the newest revision to set later and the position for comparison.
                
                NewRev(0) = xDataVal(Cnt1 + 1)
                NewRev(1) = xDataVal(Cnt1 + 2)
                Pstn = Cnt1

            End If

            'Populate forms.
            FrmsAddEntry xDataVal:=xDataVal, Cnt1:=Cnt1

            Cnt1 = Cnt1 + xDataVal(Cnt1 + 8)

        Next Cnt1
        
        'Set values of forms, only set the value of the revision number.
        'The values of the others will be set by the RevNo_Change function.
        
        .PartNoBox.Value = NewRev(0)
        .RevNoBox.Value = NewRev(1)
        
    End With

End Sub
Private Sub FrmsAddEntry(ByRef xDataVal As Variant, Optional ByRef Cnt1 As Integer)

    If IsMissing(Cnt1) Then
        Cnt1 = 0
    End If

    With Me
        FormAddItem Frm:=.PartNoBox, Val:=xDataVal(Cnt1 + 1)
        FormAddItem Frm:=.RevNoBox, Val:=xDataVal(Cnt1 + 2)
        FormAddItem Frm:=.ModByBox, Val:=xDataVal(Cnt1 + 4)
        FormAddItem Frm:=.ModForBox, Val:=xDataVal(Cnt1 + 5)
        FormAddItem Frm:=.Check1Box, Val:=xDataVal(Cnt1 + 6)
        FormAddItem Frm:=.Check2Box, Val:=xDataVal(Cnt1 + 7)
    End With
            
End Sub
Private Sub DrwLogPopSrchFrms(xDataVal As Variant)

    With Me
    
        'Clear forms on search page
        
        .PartNoFromSearch.Clear
        .PartNoToSearch.Clear
        .RevNoFromSearch.Clear
        .RevNoToSearch.Clear
        .DateFromSearch.Clear
        .DateToSearch.Clear
        .ModBySearch.Clear
        .ModForSearch.Clear
        .CheckBySearch.Clear
        
        'If there is no data exit sub.
        
        If IsMissing(xDataVal) Or IsEmpty(xDataVal) Then
            Exit Sub
        End If
        
        'Extract data and assign to appropriate forms.
        
        For Cnt1 = 0 To (UBound(xDataVal) - 9) Step 9
        
            SearchFormsAddEntry xDataVal:=xDataVal, Cnt:=Cnt1
            
            Cnt1 = Cnt1 + xDataVal(Cnt1 + 8)

        Next Cnt1

    End With

End Sub
Private Sub ClearSearchPageForms()
    With Me
        .PartNoFromSearch.ListIndex = -1
        .PartNoToSearch.ListIndex = -1
        .RevNoFromSearch.ListIndex = -1
        .RevNoToSearch.ListIndex = -1
        .DateFromSearch.ListIndex = -1
        .DateToSearch.ListIndex = -1
        .ModBySearch.ListIndex = -1
        .ModForSearch.ListIndex = -1
        .CheckBySearch.ListIndex = -1
    End With
End Sub
Private Sub DrawLogMultiPg_Change()
    With Me
    
        CntrlState = .DrawLogMultiPg.SelectedItem.Name
        
        Select Case CntrlState
            Case Is = "AddModPg"
                .OK.Left = 4
                .AddMod.Visible = True
                .Filter.Visible = False
                .Remove.Visible = True
                .ClrFrms.Visible = True
                .AttSelectBtn.Visible = False
            Case Is = "SearchPg"
                .OK.Left = 124
                .AddMod.Visible = False
                .Filter.Visible = True
                .Remove.Visible = False
                .ClrFrms.Visible = False
                .AttSelectBtn.Visible = False
            Case Is = "DataPg"
                .OK.Left = 184
                .AddMod.Visible = False
                .Filter.Visible = False
                .Remove.Visible = False
                .ClrFrms.Visible = False
                .AttSelectBtn.Visible = False
            Case Is = "Attributes"
                .OK.Left = 124
                .AddMod.Visible = False
                .Filter.Visible = False
                .Remove.Visible = False
                .ClrFrms.Visible = False
                .AttSelectBtn.Visible = True
        End Select
        
    End With
    
End Sub
Private Sub TodayDate_Click()
    Me.DateTxtBox.Value = Format(Date, "mm/dd/yyyy")
End Sub
Private Sub OK_Click()
    
    Dim xDataEntry As Variant
    Dim Test As Boolean
    
    With Me
    
        'If the multipage is not AddMod, the hide form and exit sub.
'        If .DrawLogMultiPg.SelectedItem.Name <> "AddModPg" Then
'            .hide
'            Exit Sub
'        End If
    
        'Test to see if data needs to be updated.
        Test = False
    
        xDataEntry = "DrwLog" & Trim(.RevNoBox.Value) & Trim(.PartNoBox.Value)
        ThisDrawing.Layers("0").GetXData xDataEntry, Temp1, xDtVl
               
        If Not (IsEmpty(xDtVl)) Then
        
            'Test to see if the entries do not match the form, meaning it was _
             modified and needs to be updated.
            If Trim(.PartNoBox.Value) <> xDtVl(1) Then
                Test = True
            End If
            
            If Trim(.RevNoBox.Value) <> xDtVl(2) Then
                Test = True
            End If
            
            If CDate(.DateTxtBox.Value) <> CDate(xDtVl(3)) Then
                Test = True
            End If
         
            If Trim(.ModByBox.Value) <> xDtVl(4) Then
                Test = True
            End If
        
            If Trim(.ModForBox.Value) <> xDtVl(5) Then
                Test = True
            End If
         
            If Trim(.Check1Box.Value) <> xDtVl(6) Then
                Test = True
            End If
         
            If Trim(.Check2Box.Value) <> xDtVl(7) Then
                Test = True
            End If
            
            Temp1 = ""
            For Cnt1 = 9 To 8 + xDtVl(8)
                Temp1 = Temp1 & xDtVl(Cnt1)
            Next Cnt1
            
            If Trim(.DescBox.Value) <> Temp1 Then
                Test = True
            End If
        
            'If test is true then the some entry does not match the existing _
             and the entry needs to be updated.
            If Test Then
                Temp1 = DrwLogAddModEntry
            Else
                Temp1 = False
            End If
        
        Else

            Temp1 = False
        
            'If the data is missing, then it doesn't exist and needs to be written.
            'Test to make sure that there is an entry.
            If xDataEntry <> "DrwLog" Then
                If MsgBox(Prompt:="Do you want to add this entry before exiting?", _
                            Title:=DrwLogTitle, _
                            Buttons:=vbQuestion + vbYesNo) = vbYes Then
                    Temp1 = DrwLogAddModEntry
                End If

            End If
        
        End If
        
        'If a modification to an entry was not cancelled, then test _
         to make sure that the attribute data is written correctly. _
         If everything is ok, hide the form.
         
        If Not (Test) Or (Test And Temp1) Then
            If AttWriteStatus Then
                .hide
            End If
        End If
        
    End With
    
End Sub
Private Sub Filter_Click()

    ThisDrawing.Layers("0").GetXData "", Temp1, xDataValue
    
    'If the property DwgLogData is True then all xdata is DwgLog and
    'it is not necessary to verify xData data.
'    If Not Me.DwgLogData Then
        xDataValue = VerifyDrwLogData(Dat:=xDataValue)
'    End If
    
    'Filter data.
    xDataValue = FilterData(xDataVal:=xDataValue)
    
    'If an array was returned, there is data so populate forms.
    If IsArray(xDataValue) Then
        DrwLogPopForms xDataVal:=xDataValue
        Me.DrawLogMultiPg.Value = 0
    End If
    
End Sub
Private Function FilterData(xDataVal As Variant)

    'If the clear all toggle button is true, then none of the others are
    'active, so skip the filtering.
    Dim Cnt1 As Long
    Dim Cnt2 As Long
    Dim PassedData() As Variant

    
    If ClearAllTB.Value = True Then
        FilterData = xDataVal
        Exit Function
    End If
    
    If IsMissing(xDataVal) Or IsEmpty(xDataVal) Then
        DwgError Prmpt:="This drawing does not contain Drawing Log entries."
        FilterData = "Error"
        Exit Function
    End If

    With Me
        
        For Cnt1 = 0 To (UBound(xDataVal) - 9) Step 9
        
            'If the toggle button is not pushed then populate the form with the value,
            'or if the toggle button is pushed ensure that the entry falls within the values.
            
            Temp1 = xDataVal(Cnt1 + 1)
            If (.PartNoTB.Value = True) Then
            
                'Make sure a value is set in the list.
                If (.PartNoFromSearch.ListIndex = -1) Or (.PartNoToSearch.ListIndex = -1) Then
                    DwgError Prmpt:="Value not set for Part Number Search."
                    FilterData = "Error"
                    Exit Function
                End If
                
                'Make sure from value is not greater than to value.
                If .PartNoFromSearch.Value > .PartNoToSearch.Value Then
                    DwgError Prmpt:="Value for Part Number Search From has to be" & _
                        vbCr & "less than Part Number Search To."
                    FilterData = "Error"
                    Exit Function
                End If
                
                'Check to see if value is outside of range.
                If (Temp1 < .PartNoFromSearch.Value) Or (Temp1 > .PartNoToSearch.Value) Then
                    GoTo ExcludeValue
                End If
            
            End If
            
            Temp1 = xDataVal(Cnt1 + 2)
            If (.RevNoTB.Value = True) Then
        
                'Make sure a value is set in the list.
                If (.RevNoFromSearch.ListIndex = -1) Or (.RevNoToSearch.ListIndex = -1) Then
                    DwgError Prmpt:="Value not set for Revision Number Search."
                    FilterData = "Error"
                    Exit Function
                End If
              
                'Make sure from value is not greater than to value.
                If .RevNoFromSearch.Value > .RevNoToSearch.Value Then
                    DwgError Prmpt:="Value for Revision Number Search From has to be" & _
                        vbCr & "less than Revision Number Search To."
                    FilterData = "Error"
                    Exit Function
                End If
             
                'Check to see if value is outside of range.
                If (Temp1 < .RevNoFromSearch.Value) Or (Temp1 > .RevNoToSearch.Value) Then
                    GoTo ExcludeValue
                End If
                
            End If
            
            Temp1 = CDate(xDataVal(Cnt1 + 3))
            If (.DateTB.Value = True) Then
            
                'Make sure a value is set in the list.
                If (.DateFromSearch.ListIndex = -1) Or (.DateToSearch.ListIndex = -1) Then
                    DwgError Prmpt:="Value not set for Date Search."
                    FilterData = "Error"
                    Exit Function
                End If
            
                'Make sure from value is not greater than to value.
                If CDate(.DateFromSearch.Value) > CDate(.DateToSearch.Value) Then
                    DwgError Prmpt:="Value for Date Search From has to be" & _
                        vbCr & "less than Date Search To."
                    FilterData = "Error"
                    Exit Function
                End If

                'Check to see if value is outside of range.
                If (Temp1 < CDate(.DateFromSearch.Value)) Or (Temp1 > CDate(.DateToSearch.Value)) Then
                    GoTo ExcludeValue
                End If
              
            End If
            
            If (.ModByTB.Value = True) Then
            
                'Make sure a value is set in the list.
                If (.ModBySearch.ListIndex = -1) Then
                    DwgError Prmpt:="Value not set for Modified By."
                    FilterData = "Error"
                    Exit Function
                End If
                
                'Check to see if value is outside of range.
                If (xDataVal(Cnt1 + 4) <> .ModBySearch.Value) Then
                    GoTo ExcludeValue
                End If
                
            End If
            
            If (.ModForTB.Value = True) Then
                
                'Make sure a value is set in the list.
                If (.ModForSearch.ListIndex = -1) Then
                    DwgError Prmpt:="Value not set for Modified For."
                    FilterData = "Error"
                    Exit Function
                End If

                'Check to see if value is outside of range.
                If (xDataVal(Cnt1 + 5) <> .ModForSearch.Value) Then
                    GoTo ExcludeValue
                End If
                
            End If
            
            If (.CheckByTB.Value = True) Then
                
                'Make sure a value is set in the list.
                If (.CheckBySearch.ListIndex = -1) Then
                    DwgError Prmpt:="Value not set for Checked By."
                    FilterData = "Error"
                    Exit Function
                End If
                
                'Check to see if value is outside of range.
                If (xDataVal(Cnt1 + 6) <> .CheckBySearch.Value) Then
                    GoTo ExcludeValue
                End If
                
                'Because there is two checked by's, it is necessary to check
                'both of them for data that passes.
                If (xDataVal(Cnt1 + 7) <> .CheckBySearch.Value) Then
                    GoTo ExcludeValue
                End If
                
            End If
            
            'If the routine has run to this point
            'save xDataValue entry in the PassedData variable.
                
            'Get starting point for data in PassedData array.
            On Error GoTo NoData
            Temp1 = UBound(PassedData) + 1
            GoTo SkipNoData

NoData:
            Temp1 = 0
            ReDim PassedData(8 + xDataVal(Cnt1 + 8)) As Variant
            GoTo AddData
                
SkipNoData:
            On Error GoTo 0
            ReDim Preserve PassedData(UBound(PassedData) + 9 + xDataVal(Cnt1 + 8)) As Variant
                
AddData:
            'Loop through xDataVal entry storing the data in PassedData
            For Cnt2 = Cnt1 To (Cnt1 + 8 + xDataVal(Cnt1 + 8))
                PassedData(Temp1) = xDataVal(Cnt2)
                Temp1 = Temp1 + 1
            Next Cnt2
                
ExcludeValue:
            'If there is more than one entry required for the description,then
            'the Cnt1 variable needs to be incremented accordingly.
            Cnt1 = Cnt1 + xDataVal(Cnt1 + 8)

        Next Cnt1
        
    End With
            
    FilterData = PassedData
    
End Function
Private Sub DwgError(Prmpt As String)
    MsgBox Prompt:=Prmpt, Title:=DrwLogTitle, Buttons:=vbCritical & vbOKOnly
End Sub
Private Sub Remove_Click()

    Dim FormStatus(8) As Variant

    'Get Rev Number and check to see if entry exists
    RevNo = Trim(Me.RevNoBox.Value) & Trim(Me.PartNoBox.Value)
    
    If RevNo = "" Then
        MsgBox Prompt:="A revision number and part number has not been provided.", _
               Buttons:=vbOKOnly + vbCritical, _
               Title:=DrwLogTitle
        Exit Sub
    End If
    
    CntrlState = CheckAppName("DrwLog" & RevNo)

    If CntrlState = False Then
    
        'If the entry does no exist, give message and exit sub
        
        MsgBox Prompt:="This entry does not exist.", _
               Title:=DrwLogTitle, _
               Buttons:=vbExclamation + vbOKOnly
        Exit Sub
    
    Else
    
        'Verify that the entry should be removed
    
        CntrlState = MsgBox(Prompt:="This entry will be permanently deleted." _
                        & Chr(10) & _
                        "Are you sure you want to remove this entry?", _
                        Title:=DrwLogTitle, _
                        Buttons:=vbCritical + vbYesNo)
        
        If CntrlState = vbYes Then
            
            'Remove the xdata entry.
            
            RemoveXdata ("DrwLog" & RevNo)
            
            ThisDrawing.Layers("0").GetXData "", Temp1, xDtVl
            
            'If Not Me.DwgLogData Then
                xDtVl = VerifyDrwLogData(Dat:=xDtVl)
            'End If
            
            DrwLogPopForms xDataVal:=xDtVl
    
            'Store values of forms to restore later.
            SearchFormsStoreValues Status:=FormStatus
            
            DrwLogPopSrchFrms xDataVal:=xDtVl
  
            'ReStore valuse of forms.
            SearchFormsReStoreValues Status:=FormStatus
        
        End If

    End If

End Sub
Private Sub AddMod_Click()

    Test = DrwLogAddModEntry
    
    If Test Then
        RevNo = "DrwLog" & Trim(Me.RevNoBox.Value) & Trim(Me.PartNoBox.Value)
        ThisDrawing.Layers("0").GetXData RevNo, Temp1, xDtVl
        FrmsAddEntry xDataVal:=xDtVl
        
        'After the entry has been added to the forms, the forms have to be set
        'to the newest value.  This is done by setting the part number box and
        'the revision number box and letting the event handler for these forms
        'do the rest of the work.
        
        With Me
            .PartNoBox.Value = xDtVl(1)
            .RevNoBox.Value = xDtVl(2)
        End With
    End If
    
End Sub
Private Function DrwLogAddModEntry() As Boolean
    
    'Verify that a revision number has been provided.
    
    If Trim(Me.RevNoBox.Value) = "" Then
        MsgBox Prompt:="No revision number has been provided.", _
               Buttons:=vbOKOnly + vbCritical, _
               Title:=DrwLogTitle
               
        'Return false and exit sub.
        DrwLogAddModEntry = False
        Exit Function
    
    'Verify that a part number has been provided.
    
    ElseIf Trim(Me.PartNoBox.Value) = "" Then
        MsgBox Prompt:="No part number has been provided.", _
               Buttons:=vbOKOnly + vbCritical, _
               Title:=DrwLogTitle
               
        'Return false and exit sub.
        DrwLogAddModEntry = False
        Exit Function
        
    End If
    
    'Create the name of the drawing log xdata entry.
    RevNo = "DrwLog" & Trim(Me.RevNoBox.Value) & Trim(Me.PartNoBox.Value)
    
    'Verify date data
    
    If Not (IsDate(Me.DateTxtBox.Value)) Then
        MsgBox Prompt:="Date entered is not valid.", _
               Buttons:=vbOKOnly + vbCritical, _
               Title:=DrwLogTitle
               
        'User canceled, return false and exit sub.
        DrwLogAddModEntry = False
        Exit Function
    End If
    
    'Check to see if the drawing log entry exists as a registered application name.
    
    CntrlState = CheckAppName(RevNo)
    
    If CntrlState = False Then
    
        'If the entry does not exist, add it.
        'Returns false if the xdata if full, meaning an error occured.
        
        Test = WrtDrwLogXData(RevNo)
        
        'If xdata limits is exceeded, exit this function with a failure.
        'Return false to indicate that the data was not added, preventing
        'adding the data to the forms.
        
        If Test = False Then
            DrwLogAddModEntry = False
            Exit Function
        End If
        
        'If the entry was added, tell the user that the data was successfully added.
        
        MsgBox Prompt:="Entry added.", _
                   Title:=DrwLogTitle, _
                   Buttons:=vbOKOnly + vbExclamation
        
        'Add entry to search forms
        SearchFormsGetEntry (RevNo)
        
        'Update Attributes
        ThisDrawing.Layers("0").GetXData "DwgLogAttInfo", Temp1, xDataValue
        If AttGetFormStatus(Dat:=xDataValue) Then
            AttUpdate FrmVals:=xDataValue
        End If
        
        'Entry added successful, return a true
        DrwLogAddModEntry = True

    Else
        
        'The entry was found, check to see if you want to modify it
        
        CntrlState = MsgBox(Prompt:="Are you sure you want to modify this entry?", _
                            Title:=DrwLogTitle, _
                            Buttons:=vbQuestion + vbYesNo)
        If CntrlState = vbYes Then
            
            'If yes, modify the entry
            Test = WrtDrwLogXData(RevNo)
            
            'If xdata limits is exceeded, exit this function with a failure.
            If Test = False Then
                DrwLogAddModEntry = False
                Exit Function
            End If
            
            'Add entry to search forms
            SearchFormsGetEntry (RevNo)
            
            'Update Attributes
            ThisDrawing.Layers("0").GetXData "DwgLogAttInfo", Temp1, xDataValue
            If AttGetFormStatus(Dat:=xDataValue) Then
                AttUpdate FrmVals:=xDataValue
            End If

            
            'Entry added successful, return a true
            DrwLogAddModEntry = True
        
        Else
        
            'User cancel, return false
            DrwLogAddModEntry = False
        
        End If
    End If
End Function
Private Sub SearchFormsGetEntry(xDatEntry As String)

    Dim FormStatus(8) As Variant
    
    ThisDrawing.Layers("0").GetXData xDatEntry, Temp1, xDtVl
    
    'Store values of forms to restore later.
    SearchFormsStoreValues Status:=FormStatus

    SearchFormsAddEntry xDataVal:=xDtVl, Cnt:=0
    
    'ReStore valuse of forms.
    SearchFormsReStoreValues Status:=FormStatus
    
End Sub
Private Sub SearchFormsStoreValues(ByRef Status() As Variant)
    With Me
        Status(0) = .PartNoFromSearch.ListIndex
        Status(1) = .PartNoToSearch.ListIndex
        Status(2) = .RevNoFromSearch.ListIndex
        Status(3) = .RevNoToSearch.ListIndex
        Status(4) = .DateFromSearch.ListIndex
        Status(5) = .DateToSearch.ListIndex
        Status(6) = .ModBySearch.ListIndex
        Status(7) = .ModForSearch.ListIndex
        Status(8) = .CheckBySearch.ListIndex
    End With
End Sub
Private Sub SearchFormsReStoreValues(ByRef Status As Variant)
    With Me
        .PartNoFromSearch.ListIndex = Status(0)
        .PartNoToSearch.ListIndex = Status(1)
        .RevNoFromSearch.ListIndex = Status(2)
        .RevNoToSearch.ListIndex = Status(3)
        .DateFromSearch.ListIndex = Status(4)
        .DateToSearch.ListIndex = Status(5)
        .ModBySearch.ListIndex = Status(6)
        .ModForSearch.ListIndex = Status(7)
        .CheckBySearch.ListIndex = Status(8)
    End With
End Sub
Private Sub SearchFormsAddEntry(ByRef xDataVal As Variant, Optional ByRef Cnt As Long)
    
    If IsMissing(Cnt) Then
        Cnt = 0
    End If
    
    With Me
    
        'Add part numbers to both search from and to.
            
        FormAddItem Frm:=.PartNoFromSearch, Val:=xDataVal(Cnt + 1)
        FormAddItem Frm:=.PartNoToSearch, Val:=xDataVal(Cnt + 1)
            
        'Add revision number to both search from and to.
            
        FormAddItem Frm:=.RevNoFromSearch, Val:=xDataVal(Cnt + 2)
        FormAddItem Frm:=.RevNoToSearch, Val:=xDataVal(Cnt + 2)
            
        'Add dates to both search from and to.
           
        FormAddItem Frm:=.DateFromSearch, Val:=xDataVal(Cnt + 3)
        FormAddItem Frm:=.DateToSearch, Val:=xDataVal(Cnt + 3)
            
        'Add modified by to form.
        'Add modified for to form.

        FormAddItem Frm:=.ModBySearch, Val:=xDataVal(Cnt + 4)
        FormAddItem Frm:=.ModForSearch, Val:=xDataVal(Cnt + 5)
            
        'Add both checked by 1 and checked by 2 to the checked
        'by form.
            
        FormAddItem Frm:=.CheckBySearch, Val:=xDataVal(Cnt + 6)
        FormAddItem Frm:=.CheckBySearch, Val:=xDataVal(Cnt + 7)

    End With

End Sub
Private Sub ClrFrms_Click()
    ClearForms
End Sub
Private Sub ClearForms()
    With Me
        .PartNoBox.ListIndex = -1
        .RevNoBox.ListIndex = -1
        .DateTxtBox.Value = ""
        .ModByBox.ListIndex = -1
        .ModForBox.ListIndex = -1
        .Check1Box.ListIndex = -1
        .Check2Box.ListIndex = -1
        .DescBox.Value = ""
    End With
End Sub
Private Sub PartNoTB_Change()
    With Me
        CntrlState = .PartNoTB.Value
        .PartNoFromSearch.Enabled = CntrlState
        .PartNoToSearch.Enabled = CntrlState
        .PartNoFromLabel.Enabled = CntrlState
        .PartNoToLabel.Enabled = CntrlState
    End With
    ClearAllCheck (CntrlState)
End Sub
Private Sub RevNoBox_Change()
    AutoFrmVals
End Sub
Private Sub PartNoBox_Change()
    AutoFrmVals
End Sub
Private Sub AutoFrmVals()
    
    Dim xDatCd As Variant
    Dim xDatVal As Variant
    
    With Me
        Temp1 = "DrwLog" & Trim(.RevNoBox.Value) & Trim(.PartNoBox.Value)
        ThisDrawing.Layers("0").GetXData Temp1, xDatCd, xDatVal
    
        'Ensure there is data.
        If Not (IsEmpty(xDatVal)) Then

            .PartNoBox.Value = xDatVal(1)
            .RevNoBox.Value = xDatVal(2)
            .DateTxtBox.Value = xDatVal(3)
            .ModByBox.Value = xDatVal(4)
            .ModForBox.Value = xDatVal(5)
            .Check1Box.Value = xDatVal(6)
            .Check2Box.Value = xDatVal(7)

            Temp1 = ""
            For Cnt1 = 9 To 8 + xDatVal(8)
                Temp1 = Temp1 & xDatVal(Cnt1)
            Next Cnt1
            
            .DescBox.Value = Temp1
            
        Else

            .DateTxtBox.Value = ""
            .ModByBox.ListIndex = -1
            .ModForBox.ListIndex = -1
            .Check1Box.ListIndex = -1
            .Check2Box.ListIndex = -1
            .DescBox.Value = ""
        
        End If
        
    End With
    
End Sub
Private Sub RevNoTB_Change()
    With Me
        CntrlState = .RevNoTB.Value
        .RevNoFromSearch.Enabled = CntrlState
        .RevNoToSearch.Enabled = CntrlState
        .RevNoFromLabel.Enabled = CntrlState
        .RevNoToLabel.Enabled = CntrlState
    End With
    ClearAllCheck (CntrlState)
End Sub
Private Sub DateTB_Change()
    With Me
        CntrlState = .DateTB.Value
        .DateFromSearch.Enabled = CntrlState
        .DateToSearch.Enabled = CntrlState
        .DateFromLabel.Enabled = CntrlState
        .DateToLabel.Enabled = CntrlState
    End With
    ClearAllCheck (CntrlState)
End Sub
Private Sub ModByTB_Change()
    With Me
        CntrlState = .ModByTB.Value
        .ModBySearch.Enabled = CntrlState
    End With
    ClearAllCheck (CntrlState)
End Sub
Private Sub ModForTB_Change()
    With Me
        CntrlState = .ModForTB.Value
        .ModForSearch.Enabled = CntrlState
    End With
    ClearAllCheck (CntrlState)
End Sub
Private Sub CheckByTB_Change()
    With Me
        CntrlState = .CheckByTB.Value
        .CheckBySearch.Enabled = CntrlState
    End With
    ClearAllCheck (CntrlState)
End Sub
Private Sub ClearAllTB_Change()
    With Me
        If .ClearAllTB.Value = True Then
            .PartNoTB.Value = False
            .RevNoTB.Value = False
            .DateTB.Value = False
            .ModByTB.Value = False
            .ModForTB.Value = False
            .CheckByTB.Value = False
        ElseIf (.ClearAllTB.Value = False) And _
               (.PartNoTB.Value = False) And _
               (.RevNoTB.Value = False) And _
               (.DateTB.Value = False) And _
               (.ModByTB.Value = False) And _
               (.ModForTB.Value = False) And _
               (.CheckByTB.Value = False) Then
            .ClearAllTB.Value = True
        End If
    End With
End Sub
Private Sub DataClearTB_Change()
    With Me
        If .DataClearTB.Value = True Then
            .DataClearWarnTxt.Caption = "Warning:  All Data Will Be Erased!"
        Else
            .DataClearWarnTxt.Caption = ""
        End If
    End With
End Sub
Private Sub ClearAllCheck(CntrlState)
    With Me
        If CntrlState = True Then
            .ClearAllTB = False
        ElseIf (.PartNoTB = False) And _
               (.RevNoTB = False) And _
               (.DateTB = False) And _
               (.ModByTB = False) And _
               (.ModForTB = False) And _
               (.CheckByTB = False) Then
            .ClearAllTB = True
        End If
    End With
End Sub
Private Function WrtDrwLogXData(ByRef RegAppName As String) As Boolean
    
    Dim xDataCode() As Integer
    Dim xDataValue() As Variant
    
    ReDim xDataCode(9)
    ReDim xDataValue(9)
    
    'Add the application name

    xDataCode(0) = 1001
    xDataValue(0) = RegAppName
    
    'Set the entries in xdatacode to contain the string code.
    For Cnt1 = 1 To 7
        xDataCode(Cnt1) = 1000
    Next Cnt1
    
    xDataCode(8) = 1071
    xDataCode(9) = 1000

    'Gather the data from the form and store it in the arrays
    With Me
        xDataValue(1) = Trim(.PartNoBox.Value)
        xDataValue(2) = Trim(.RevNoBox.Value)
        xDataValue(3) = CStr(Format(CDate(.DateTxtBox.Value), "mm/dd/yyyy"))
        xDataValue(4) = Trim(.ModByBox.Value)
        xDataValue(5) = Trim(.ModForBox.Value)
        xDataValue(6) = Trim(.Check1Box.Value)
        xDataValue(7) = Trim(.Check2Box.Value)
        xDataValue(9) = Trim(.DescBox.Value)
    End With
    
    'AutoCAD can only store 255 characters per entry.
    If Len(xDataValue(9)) > 255 Then
    
        'Determine the number of extra entries needed.
        Cnt2 = Fix(Len(xDataValue(9)) / 255)
        
        'Store the number of strings required to hold the description.
        xDataValue(8) = Cnt2 + 1
        
        'Set cnt2 to be the start of the extra strings.
        Cnt2 = Cnt2 + 9
        
        'Resize the variables to provide enough room for string.
        ReDim Preserve xDataValue(Cnt2) As Variant
        ReDim Preserve xDataCode(Cnt2) As Integer
        
        'Set entries in xdatacode to contain the string code.
        For Cnt1 = 10 To Cnt2
            xDataCode(Cnt1) = 1000
        Next Cnt1
        
        'Store value so that it can be divided and stored into separate 255 character
        'length entries.
        Temp1 = xDataValue(9)
        
        'Divide and store text entries separate spaces.
        For Cnt1 = 9 To Cnt2
            xDataValue(Cnt1) = Left(Temp1, 255)
            Temp1 = Mid(Temp1, 256, Len(Temp1))
        Next Cnt1
        
    Else
    
        'Store the number of strings required to hold the description.
        xDataValue(8) = 1
        
    End If
    
    On Error GoTo xDataLimitExceed
    ThisDrawing.Layers("0").SetXData xDataCode, xDataValue
    
    'Store the registered application name in the attribute data so it can retrieve it.
    
    ThisDrawing.Layers("0").GetXData "DwgLogAttInfo", Temp1, xDtVl
    
    xDtVl(20) = RegAppName
    ThisDrawing.Layers("0").SetXData Temp1, xDtVl

    GoTo NoErrorExit:
    
xDataLimitExceed:
    MsgBox Prompt:="The allowable size of data has been exceeded." & vbCr & _
        "Please export and clear the data and try again.", _
        Title:=DrwLogTitle
        
    WrtDrwLogXData = False
    Exit Function

NoErrorExit:
    On Error GoTo 0
    WrtDrwLogXData = True
    
End Function
Private Sub DataExp_Click()
    NewExcelFile
End Sub
Private Sub NewExcelFile()

    Dim aDoc As Object
    Dim aSheet As Object
    Dim ExcelApp As Object
    Dim NumEntry As Integer
    Dim RowCnt As Long

    Const StrtCell As String = "B2"
    
    NumEntry = 7
    
    Set aDoc = AutoCAD.Application.ActiveDocument
    
    ThisDrawing.Layers("0").GetXData "", Temp1, xDataValue
    
    'If DwgLogData is false, the the layer 0 contains xData that is not
    'from DrwLog and it must be removed.

     'If Not Me.DwgLogData Then
     xDataValue = VerifyDrwLogData(Dat:=xDataValue)
     'End If

    'Verify that this drawing contains DrwLog entrys after the non DrwLog xData
    'has been removed.
    If IsEmpty(xDataValue) Then
        MsgBox Prompt:="This drawing does not contain any Drawing Log entries.", _
            Title:=DrwLogTitle, _
            Buttons:=vbCritical + vbOKOnly
        Exit Sub
    End If

    'Check to see if data is to be removed.
    If Me.DataClearTB.Value = True Then
    
        'Remove the data.
        RemoveAllxData xDat:=xDataValue
        
        'Clear the froms
        DrwLogPopForms xDataVal:=Empty
        ClearForms
        DrwLogPopSrchFrms xDataVal:=Empty
        ClearSearchPageForms
        
    End If
    
    aDoc.SetVariable "modemacro", "Initilizing Excel..."
    
    'Get data from config file
    
    'Initilize variables
    FileNum = FreeFile
    DwgLogFile = GetDwgLogCfgFile
    
    'Insure data exists to prevent errors
    InsureConfigData FileName:=DwgLogFile
    
    'Open the config file for input
    Open DwgLogFile For Input As #FileNum
    
    'Read in the config data and store in the ConfigDat array variable
    Cnt1 = 0
    
    Do While Not EOF(FileNum)
        
        'Read in a line
        Line Input #FileNum, Temp1
        
        ConfigDat(Cnt1) = CInt(Temp1)
            
        'Increment counter
        Cnt1 = Cnt1 + 1
        
    Loop
    
    'Close the file.
    Close #FileNum
    
    'Create a new Excel object
    Set ExcelApp = CreateObject("Excel.Application")
    
    'Set up sheets
    With ExcelApp
        Temp1 = .SheetsInNewWorkbook
        .SheetsInNewWorkbook = 1
        .Workbooks.Add
        .SheetsInNewWorkbook = Temp1
        .ActiveWindow.Zoom = 85
    End With
    
    Set aSheet = ExcelApp.ActiveSheet

    With aSheet
    
        .Name = "Drawing Log"
        .Columns("A:A").ColumnWidth = 2.86

        'Label column headings.
        With .Range(StrtCell)
            .Offset(1, 0).FormulaR1C1 = "Part No."
            .Offset(1, 1).FormulaR1C1 = "Rev No."
            .Offset(1, 2).FormulaR1C1 = "Date"
            .Offset(1, 3).FormulaR1C1 = "Modified By"
            .Offset(1, 4).FormulaR1C1 = "Modified For"
            .Offset(1, 5).FormulaR1C1 = "Checked By 1"
            .Offset(1, 6).FormulaR1C1 = "Checked By 2"
            .Offset(1, 7).FormulaR1C1 = "Description"
        End With

        'Add data to sheet.
        
        'Step through each drawing log entry.
        RowCnt = 2
        For Cnt1 = 0 To (UBound(xDataValue) - 9) Step 9
        
            'Step through each value in the log entry.
            For Cnt2 = 1 To 7
                    
               .Range(StrtCell).Offset(RowCnt, (Cnt2 - 1)).FormulaR1C1 = xDataValue(Cnt1 + Cnt2)
            
            Next Cnt2
            
            'Get all the description entries and put into cell.
            Temp1 = ""
            For Cnt2 = 9 To 8 + xDataValue(Cnt1 + 8)
                Temp1 = Temp1 & xDataValue(Cnt1 + Cnt2)
            Next Cnt2
            .Range(StrtCell).Offset(RowCnt, NumEntry).FormulaR1C1 = Temp1
            
            'Outline the borders.
            OutLineBorders Sht:=aSheet, Strt:=.Range(StrtCell).Offset(RowCnt, 0).Address, Numb:=NumEntry
            
            'Increment row counter.
            RowCnt = RowCnt + 1
            
            'If there is more than one description entry the cnt1 needs to be incremented also
            Cnt1 = Cnt1 + xDataValue(Cnt1 + 8)

        Next Cnt1
        
        'Sort data.
        .Range(.Range(StrtCell).Offset(2, 0), .Range(StrtCell).Offset(RowCnt, NumEntry)).Sort _
             Key1:=.Range(StrtCell).Offset(2, 1), Order1:=1, Key2:=.Range(StrtCell).Offset(2, 2) _
             , Order2:=1, Key3:=.Range(StrtCell).Offset(2, 0), Order3:=1, Header:= _
             2, OrderCustom:=1, MatchCase:=False, Orientation:=1

        'Format columns.
        With .Range(StrtCell)
        
            For Cnt1 = 0 To 7
            
                If ConfigDat(Cnt1) = 0 Then
                
                    'If it is zero, delete column
                    'Delete column and shift to left, xlToLeft
                    ExcelApp.ActiveSheet.Columns(Cnt1 + 2).Delete Shift:=-4159
                    
                    'Check to see if it is to exported, increment the number
                    'of entries if it is to be exported.
                    NumEntry = NumEntry - 1
                
                Else
                
                    'Revision number.
                    .Offset(0, (Cnt1 - (7 - NumEntry))).EntireColumn.ColumnWidth = ConfigDat(Cnt1)
                    
                End If
                
            Next Cnt1
            
            'Format date column
            If ConfigDat(2) <> 0 Then
                With .Offset(0, 2).EntireColumn
                    .NumberFormat = "mm/dd/yyyy"
                End With
            End If
            
            For Cnt1 = 0 To NumEntry
                With .Offset(1, Cnt1).EntireColumn
                    'Vertical alignment xlTop
                    .VerticalAlignment = -4160
                    .WrapText = True
                End With
            Next Cnt1
            
            'Outline borders for header columns.
            OutLineBorders Sht:=aSheet, Strt:=.Offset(1, 0).Address, Numb:=NumEntry
        
        End With
        
        'Create title.
        With .Range(StrtCell)
            .FormulaR1C1 = "Drawing Log Data"
            With .Font
                .Name = "Arial"
                .Bold = True
                .Size = 12
                .Strikethrough = False
                .Superscript = False
                .Subscript = False
                .OutlineFont = False
                .Shadow = False
                .Underline = -4142
                .ColorIndex = -4105
            End With
        End With
       
        OutLineBorders Sht:=aSheet, Strt:=StrtCell, Numb:=NumEntry
        
        With .Range(StrtCell, .Range(StrtCell).Offset(0, NumEntry))
            .HorizontalAlignment = 7
            .Borders(11).LineStyle = -4142
        End With

        'Format column headings.
        With .Range(.Range(StrtCell).Offset(1, 0), .Range(StrtCell).Offset(1, NumEntry))
            .Font.Bold = True
            .HorizontalAlignment = -4108
            .VerticalAlignment = -4107
            .WrapText = False
            .Orientation = 0
            .AddIndent = False
            .ShrinkToFit = False
            .MergeCells = False
            
            .Select
        End With
        
        'Apply filters
        ExcelApp.Selection.AutoFilter

        'Select cell A1.
        .Range("A1").Select
    
    End With
    
    aDoc.SetVariable "modemacro", ""
    
    ExcelApp.Visible = True
    
End Sub
Private Sub RemoveAllxData(xDat As Variant)
    For Cnt1 = 0 To (UBound(xDat) - 9) Step 9
        RemoveXdata RegAppName:=CStr(xDat(Cnt1))
        Cnt1 = Cnt1 + xDat(Cnt1 + 8)
    Next Cnt1
End Sub
Private Sub OutLineBorders(Sht As Object, Strt As String, Numb As Integer)
    With Sht.Range(Strt, Sht.Range(Strt).Offset(0, Numb))
        .Borders(5).LineStyle = -4142
        .Borders(6).LineStyle = -4142
        With .Borders(7)
            .LineStyle = 1
            .Weight = 2
            .ColorIndex = -4105
        End With
        With .Borders(8)
            .LineStyle = 1
            .Weight = 2
            .ColorIndex = -4105
        End With
        With .Borders(9)
            .LineStyle = 1
            .Weight = 2
            .ColorIndex = -4105
        End With
        With .Borders(10)
            .LineStyle = 1
            .Weight = 2
            .ColorIndex = -4105
        End With
        With .Borders(11)
            .LineStyle = 1
            .Weight = 2
            .ColorIndex = -4105
        End With
    End With

End Sub
Private Sub StandImpCB_Click()
    ImportStandards
End Sub
Sub ImportStandards()

    'Declare variables
    Dim Cnt1 As Long
    Dim FormVal As String
    Dim Line1 As String
    
    'Initilize variables
    FileNum = FreeFile
    DwgLogFile = GetStandardsFile
    
    InsureStandardsFile FileName:=DwgLogFile
    
    'Open the config file for input
    Open DwgLogFile For Input As #FileNum
    
    Do
        Line1 = GetNewLine(FileNumber:=FileNum)
    Loop Until (Left(Line1, 2) = "**") Or (Line1 = "")
    Line1 = GetNewLine(FileNumber:=FileNum)
    
    For Cnt1 = 1 To 6
        Set DwgFrm = GetDrwLogFrm(Number:=Cnt1)
        Do Until (Left(Line1, 2) = "**") Or (Line1 = "")
            FormVal = DwgFrm.Value
            FormAddItem Frm:=DwgFrm, Val:=Line1
            DwgFrm.Value = FormVal
            Line1 = GetNewLine(FileNumber:=FileNum)
        Loop
        Line1 = GetNewLine(FileNumber:=FileNum)
    Next Cnt1
    
    'Close the file
    Close #FileNum
    
    'Give a message stating the operation was completed.
    MsgBox Prompt:="Standard Data Imported.", _
           Title:=DrwLogTitle, _
           Buttons:=vbOKOnly + vbExclamation

End Sub
Private Sub StandExpCB_Click()
    ExportStandards
End Sub
Sub ExportStandards()

    'Declare variables
    Dim Cnt1 As Long
    Dim FileNum2 As Long
    Dim LstVal As String
    Dim Line1 As String
      
    'Initilize variables
    FileNum = FreeFile
    DwgLogFile = GetStandardsFile
    
    InsureStandardsFile FileName:=DwgLogFile
    
    With Me
    
        'If the TB is true the the existing data in the file is to be
        'over written.
        
        If .StandOverWrtTB.Value = True Then
        
            'Open the config file for output.
            Open DwgLogFile For Output As #FileNum
            
            'Loop through the forms and write the data to the file.
            For Cnt1 = 1 To 6
            
                'Get the form to use from the getdrwlogfrm utility.
                Set DwgFrm = GetDrwLogFrm(Number:=Cnt1)
                
                'Write the appropriate header line to the file.
                'Using the print statement instead of the write prevents the
                'quotation delimiters from being written.
                Print #FileNum, GetStandFileHeader(Number:=Cnt1)
                
                'Store the current value of the form.
                LstVal = DwgFrm.Value
                
                'Loop through the values in the form and write them to the file.
                WriteFormVals DwgFrm:=DwgFrm, FileNum:=FileNum, Prefix:="    "

                'Restore the form to its initial value.
                DwgFrm.Value = LstVal

            Next Cnt1

            'Close the standard file.
            Close #FileNum

        Else
            'Else, the contents are to be appended to, not overwritten.

            'Copy the file.

            Temp1 = GetTempFile

            FileCopy Source:=DwgLogFile, Destination:=Temp1
            
            'Open the config file for input.
            Open DwgLogFile For Output As #FileNum

            'Open the temp file for output.
            FileNum2 = FreeFile
            Open Temp1 For Input As #FileNum2

            Do
                Line1 = GetNewLine(FileNumber:=FileNum2)
            Loop Until (Left(Line1, 2) = "**") Or (Line1 = "")
            Line1 = GetNewLine(FileNumber:=FileNum2)
            
            For Cnt1 = 1 To 6

                'Get the form to use from the getdrwlogfrm utility.
                Set DwgFrm = GetDrwLogFrm(Number:=Cnt1)
                
                'Write the appropriate header line to the file.
                Print #FileNum, GetStandFileHeader(Number:=Cnt1)
                
                'Store the current value of the form.
                LstVal = DwgFrm.Value

                'Write the old data to the file.
                Do Until (Left(Line1, 2) = "**") Or (Line1 = "")

                    'Verify that the data isn't in the form.  This ensures that the
                    'data will not be written twice.
                    If Not (CheckFormForVal(Frm:=DwgFrm, Val:=Line1)) Then
                        Print #FileNum, ("    " & Line1)
                    End If
                    Line1 = GetNewLine(FileNumber:=FileNum2)

                Loop
                Line1 = GetNewLine(FileNumber:=FileNum2)
                
                'Loop through the values in the form and write them to the file.
                WriteFormVals DwgFrm:=DwgFrm, FileNum:=FileNum, Prefix:="    "
                
                'Restore the form to its initial value.
                DwgFrm.Value = LstVal

            Next Cnt1
            
            'Close files.
            Close #FileNum
            Close #FileNum2
            
            'Delete the temp file.
            Kill PathName:=GetTempFile
        
        End If

    End With

   'Give a message stating the operation was completed.
    MsgBox Prompt:="Standard Data Exported.", _
           Title:=DrwLogTitle, _
            Buttons:=vbOKOnly + vbExclamation

End Sub
Private Function GetStandFileHeader(Number As Long) As String
    Select Case Number
        Case 1
            GetStandFileHeader = "**Part Number"
        Case 2
            GetStandFileHeader = "**Revision Number"
        Case 3
            GetStandFileHeader = "**Modified By"
        Case 4
            GetStandFileHeader = "**Modified For"
        Case 5
            GetStandFileHeader = "**Checked By 1"
        Case 6
            GetStandFileHeader = "**Checked by 2"
    End Select
End Function
Private Function GetDrwLogFrm(Number As Long) As Object
    With Me
        Select Case Number
            Case 1
                Set GetDrwLogFrm = .PartNoBox
            Case 2
                Set GetDrwLogFrm = .RevNoBox
            Case 3
                Set GetDrwLogFrm = .ModByBox
            Case 4
                Set GetDrwLogFrm = .ModForBox
            Case 5
                Set GetDrwLogFrm = .Check1Box
            Case 6
                Set GetDrwLogFrm = .Check2Box
        End Select
    End With
End Function
Private Sub StandOverWrtTB_Change()
    With Me
        If .StandOverWrtTB.Value = True Then
            .StandOverWrtWarnTxtLbl.Caption = "Warning:  All Data Will Be Overwritten!"
        Else
            .StandOverWrtWarnTxtLbl.Caption = ""
        End If
    End With
End Sub
Private Sub Cancel_Click()
    Me.hide
End Sub

Attribute VB_Name = "DrawLogUtils"
Option Explicit
Option Private Module
Public Cnt1 As Long
Public Cnt2 As Long
Public ConfigDat(7) As Variant
Public DwgLogFile As String
Public FileNum As Long
Public Temp1 As Variant
Public Test As Boolean
Public Const DrwLogTitle As String = "Drawing Log"
Function GetDwgLogCfgFile() As String
    GetDwgLogCfgFile = ParsePath(GetDwgLogPath) & "drawinglog.cfg"
End Function
Function GetStandardsFile() As String
    GetStandardsFile = ParsePath(GetDwgLogPath) & "drawinglog.std"
End Function
Function GetTempFile() As String
    GetTempFile = ParsePath(GetDwgLogPath) & "dwglogtemp.txt"
End Function
Function GetDwgLogPath() As String
    GetDwgLogPath = SearchAcadPath(FileNm:="drawinglog.dvb")
End Function
Sub InsureConfigData(FileName As String)
    Temp1 = Dir(FileName)
    If Temp1 = "" Then
        FileNum = FreeFile
        Open FileName For Output As #FileNum
        Write #FileNum, 12
        Write #FileNum, 12
        Write #FileNum, 10
        For Cnt1 = 3 To 6
            Write #FileNum, 18
        Next Cnt1
        Write #FileNum, 38
        Close #FileNum
    End If
End Sub
Sub InsureStandardsFile(FileName As String)
    Temp1 = Dir(FileName)
    If Temp1 = "" Then
        FileNum = FreeFile
        Open FileName For Output As #FileNum
        Write #FileNum, " "
        Close #FileNum
    End If
End Sub
Function VerifyDrwLogData(ByRef Dat As Variant) As Variant
    
    'Declare variables.
    Dim PassedData() As Variant
    ReDim PassedData(8) As Variant
    
    'Initiate variables.
    Test = False
    Temp1 = 0
    
    If IsMissing(Dat) Or IsEmpty(Dat) Then
        VerifyDrwLogData = Empty
        Exit Function
    End If
    
   On Error GoTo EndOfData
        
    For Cnt1 = 0 To (UBound(Dat) - 9) Step 9
    
        Do While (Cnt1 < UBound(Dat) - 9) And (Left(Dat(Cnt1), 6) <> "DrwLog")
            Cnt1 = Cnt1 + 1
        Loop

        'Loop through Dat entry storing the data in PassedData
            
        If UBound(PassedData) = 8 Then
            ReDim Preserve PassedData(UBound(PassedData) + Dat(Cnt1 + 8)) As Variant
        Else
            ReDim Preserve PassedData(UBound(PassedData) + 9 + Dat(Cnt1 + 8)) As Variant
        End If
            
        For Cnt2 = Cnt1 To (Cnt1 + 8 + Dat(Cnt1 + 8))
            PassedData(Temp1) = Dat(Cnt2)
            Temp1 = Temp1 + 1
        Next Cnt2
            
        Cnt1 = Cnt1 + Dat(Cnt1 + 8)
            
        Test = True
            
    Next Cnt1
    
EndOfData:
    
    If Test = True Then
        VerifyDrwLogData = PassedData
    Else
        VerifyDrwLogData = Empty
    End If
    
End Function

Attribute VB_Name = "FormUtils"
Option Explicit
Option Private Module
Private Cnt1 As Integer
Public Sub FormAddItem(ByRef Frm As Object, ByRef Val As Variant)
    
    'If the value was not found add it
    
    If Not (CheckFormForVal(Frm:=Frm, Val:=Val)) Then
        Frm.AddItem (Val)
    End If

End Sub
Public Function CheckFormForVal(ByRef Frm As Object, ByRef Val As Variant) As Boolean

    'If the list does not contain data an error will result.
    'To prevent, capture error and skip to adding entry.
    'Cannot test for missing data with IsEmpty or IsNull.
  
    On Error GoTo EmptyList
    
    For Cnt1 = 0 To (Frm.ListCount - 1)
        Frm.ListIndex = Cnt1
        If Frm.Value = Val Then
            CheckFormForVal = True
            Exit Function
        End If
    Next Cnt1
    
EmptyList:
    CheckFormForVal = False

End Function
Public Sub FormRemoveItem(ByRef Frm As Object, ByRef Val As Variant)
    
    'If the list does not contain data an error will result.
    'To prevent, capture error and skip to adding entry.
    'Cannot test for missing data with IsEmpty or IsNull.
    
    On Error GoTo EmptyList
    
    For Cnt1 = 0 To (Frm.ListCount - 1)
        Frm.ListIndex = Cnt1
        If Frm.Value = Val Then
            Frm.RemoveItem (Cnt1)
            Exit Sub
        End If
    Next Cnt1
    
EmptyList:

End Sub
Public Sub WriteFormVals(ByRef DwgFrm As Object, ByRef FileNum As Long, Optional ByRef Prefix As String)
    
    For Cnt2 = 0 To (DwgFrm.ListCount - 1)
                    
        'Index the form setting.
        DwgFrm.ListIndex = Cnt2
                    
        'Get the index value.
        Temp1 = Prefix & Trim(DwgFrm.Value)
                   
        'Write the data to the file.
        Print #FileNum, Temp1
                   
    Next Cnt2

End Sub

Attribute VB_Name = "PathFileUtils"
Option Explicit
Option Base 0
Option Private Module
Private Cnt1 As Integer
Public Const MaxPathLen = 260
Public Declare PtrSafe Function SearchPath Lib "kernel32" Alias "SearchPathA" _
    (ByVal lPth As String, _
     ByVal lFName As String, _
     ByVal lExt As String, _
     ByVal nBffrLngth As Long, _
     ByVal lBffr As String, _
     ByVal lFlPrt As String) As Long
Public Function SearchAcadPath(FileNm As String)

    Dim Pth As String
    
    Pth = ThisDrawing.Application.Path & ";" & ThisDrawing.Application.Preferences.Files.SupportPath
    Pth = FindFile(FileName:=FileNm, SrchPath:=Pth)
    SearchAcadPath = Pth
End Function
Public Function FindFile(FileName As String, Optional SrchPath As String = vbNullString) As String
    
    Dim Temp1 As Long, lBffr As String * MaxPathLen
    
    Temp1 = SearchPath(SrchPath, FileName, vbNullString, MaxPathLen, lBffr, vbNullString)
    If Temp1 Then
        FindFile = Left(lBffr, Temp1)
    Else
        FindFile = "Not Found"
    End If

End Function
Public Function ParsePath(fPath As String) As Variant

    Dim Temp1 As Variant
    
    Temp1 = Split(fPath, "\")
    
    For Cnt1 = 0 To (UBound(Temp1) - 1)
        ParsePath = ParsePath & Temp1(Cnt1) & "\"
    Next Cnt1

End Function
Public Function GetNewLine(FileNumber As Long)
    
    Dim Line1 As String

    Do While Line1 = ""
        If Not EOF(FileNumber) Then
            Line Input #FileNumber, Line1
            Line1 = Trim(Line1)
        Else
            GoTo EndOfFile
        End If
    Loop
    
EndOfFile:
    GetNewLine = Line1

End Function

Attribute VB_Name = "SelectUtils"
Option Base 0
Option Explicit
Option Private Module
Private ActDwgUtility As Object
Private ActDwgSS As Object
Private Item As Object
Private Temp1 As Variant
Public Function SSExists(ByRef SSName As String, ByRef SelectSets As Object) As Boolean
    For Each Item In SelectSets
        If Item.Name = Name Then
            SSExists = True
            Exit Function
        End If
    Next Item
End Function
Public Sub DeleteSS(ByRef SSName As String)
    Set ActDwgSS = ThisDrawing.SelectionSets
    If SSExists(SSName:=SSName, SelectSets:=ActDwgSS) Then
        ActDwgSS.Item(SSName).Delete
    End If
End Sub
Public Sub AddSS(ByRef SSName As String)
    Set ActDwgSS = ThisDrawing.SelectionSets
    If Not SSExists(SSName:=SSName, SelectSets:=ActDwgSS) Then
        ActDwgSS.Add SSName
    End If
End Sub
Public Sub EntSel(ByRef Ent As Variant, Optional ByRef Prmpt As String, Optional ByRef Filter As String)
    
    'Convert case to insure it's correct.
    Filter = LCase(Filter)
    Set ActDwgUtility = ThisDrawing.Utility
    
    'Trap error to ensure entity is selected.
    On Error GoTo NoEnt:
    
    'Loop until the correct entity type is selected.
SelectEnt:
    ActDwgUtility.GetEntity Item, Temp1, Prmpt
    If Filter <> "" Then
        If LCase(Item.ObjectName) <> Filter Then GoTo WrongEntType
    End If
    GoTo CorrectEnt
    
NoEnt:
    MsgBox Prompt:="An entity was not selected.", Title:=DrwLogTitle, Buttons:=vbCritical + vbOKOnly
    Ent = False
    Exit Sub
    
WrongEntType:
    ActDwgUtility.Prompt (vbCrLf & "That entity is not the correct type.")
    GoTo SelectEnt

CorrectEnt:

    'Restore error handling
    On Error GoTo 0
    
    Set Ent = Item
    
End Sub
Public Sub GetAttBlock(AttBlock As Variant)

    Set ActDwgUtility = ThisDrawing.Utility

SelectEnt:
    EntSel Ent:=AttBlock, Prmpt:=vbCrLf & "Select an attributed block: ", Filter:="AcDbBlockReference"
    If VarType(AttBlock) = 9 Then
        If Not (AttBlock.HasAttributes) Then
            ActDwgUtility.Prompt (vbCrLf & "That block does not have attributes.")
            GoTo SelectEnt:
        End If
    End If

End Sub

Attribute VB_Name = "XDataUtils"
Option Explicit
Option Base 0
Option Private Module
Private Cnt1 As Integer
Public Sub RemoveXdata(ByVal RegAppName As String)
    Dim xDataCode(0) As Integer
    Dim xDataValue(0) As Variant
    
'   Add the application name

    xDataCode(0) = 1001
    xDataValue(0) = RegAppName

'   Clear the data by setting only application name
    
    ThisDrawing.Layers("0").SetXData xDataCode, xDataValue
    RemoveAppName RegAppName:=RegAppName
    
End Sub
Public Function GetAppName(RegAppName As String) As String
    Cnt1 = 0
    On Error Resume Next
    With ThisDrawing.RegisteredApplications
        Do
            Cnt1 = Cnt1 + 1
            Err.Clear
            .Item (Name & Str(Cnt1))
        Loop Until Err.Number <> 0
        .Add (RegAppName & Str(Cnt1))
    End With
    GetAppName = RegAppName & Str(Cnt1)
End Function
Public Function CheckAppName(RegAppName As String) As Boolean
    
    Dim RegApp As Object
  
'   Initialize varaible
  
    CheckAppName = False
  
        For Each RegApp In ThisDrawing.RegisteredApplications
            
            'If name is found, set checkappname to true
            
            If RegApp.Name = RegAppName Then
                CheckAppName = True
                GoTo AppNameFound
            End If
        Next RegApp
        
AppNameFound:
    CheckAppName = CheckAppName
    
End Function
Public Sub RemoveAppName(RegAppName As String)
    ThisDrawing.RegisteredApplications.Item(RegAppName).Delete
End Sub
