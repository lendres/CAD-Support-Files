Attribute VB_Name = "TestMod"
Option Base 0
Option Explicit
Dim Test1 As Object
Dim Item As Object
Dim Temp1 As Variant
Dim ActDwgUtility As Object
Public Sub RunVBTest()
    Set Temp1 = ThisDrawing.HandleToObject("64")
    MsgBox Prompt:=Temp1.Name, title:="Testing"
End Sub
